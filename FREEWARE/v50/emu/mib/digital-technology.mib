-- Title:       DIGITAL TECHNOLOGY INC. MIB
	-- Date:        September 13, 1993


	--*******************************************************
	--
	-- This MIB defines DTI agent MIB on FDDI.
	-- It can go up to 16 FDDI boards. Each board
	-- has 2 ports (PhyA and PhyB). Each port defines as 
	-- DtiFddiSdbList which contains 7 DtiFddiSdbList 
	-- in the following:
	--
	--      Sdb Name                Sdb	Comments
	--      dtiFddiSdbTokenTimer    0       Token rotation time
	--      dtiFddiSdbTokenCount    1       Token count
	--      dtiFddiSdbFrameError    2       Error count
	--      dtiFddiSdbNopCount      3       Ring non-ops
	--      dtiFddiSdbFrameCount    4       Frame count
	--      dtiFddiSdbByteCount     5       Byte count
	--      dtiFddiSdbAvgFrame      6       Anerage frame size
	--
	-- Also each above DtiFddiSdbList has DtiFddiSdb structure:
	--
	--      Name            Size            Comments 
	--      SdbCcnt    (Counter64)     Counts in current sampling
	--      SdbRmin    (Counter64)     Minimum counts from beginning
	--      SdbRmax    (Counter64)     Maximum counts from beginning
	--      SdbRcnt    (Counter64)     Total counts from beginning
	--      SdbRsmp    (Counter64)     Total sampling counts
	--
	--********************************************************


	--This document describes the variables in the Enterprise DTI MIB. 
	--The variables are structured based on the RFC for the Structure of
	--Management Information (SMI), RFC1155, and the format of the 
	--definitions is as per RFC1212, the Concise MIB Defintions.

	DTI-MIB  { iso(1) org(3) dod(6) internet(1) private(4) 
		   enterprises(1) dti(725) }

	DEFINITIONS ::= BEGIN

	IMPORTS
		enterprises, OBJECT-TYPE
		FROM RFC1155-SMI;

	-- textual conventions

	Counter64 ::= INTEGER (0..18446744073709551615)

	dti     OBJECT IDENTIFIER ::= { enterprises 725 }

	-- groups in the DTI-MIB

	fddi    OBJECT IDENTIFIER ::= { dti 1 }
	--atm     OBJECT IDENTIFIER ::= { dti 2 }

	-- object types

	dtiFddiTable	OBJECT-TYPE
		SYNTAX	SEQUENCE OF DtiFddiSdbEntry
		ACCESS  not-accessible
		STATUS  mandatory
		::= { fddi 1 }
 
	dtiFddiSdbEntry OBJECT-TYPE
		SYNTAX  DtiFddiSdbEntry
		ACCESS  not-accessible
		STATUS  mandatory
		INDEX   { dtiFddiBoard, dtiFddiPort, dtiFddiSdb }        
		::= { dtiFddiTable 1 }

	DtiFddiSdbEntry ::=       
		SEQUENCE {
			dtiFddiBoard
				INTEGER,
			dtiFddiPort
				INTEGER,
			dtiFddiSdb
				INTEGER,
			dtiFddiSdbCcnt
				Counter64,
			dtiFddiSdbRmin
				Counter64,
			dtiFddiSdbRmax
				Counter64,
			dtiFddiSdbRcnt
				Counter64,
			dtiFddiSdbRsmp
				Counter64
		}

	dtiFddiBoard	OBJECT-TYPE
		SYNTAX  INTEGER
		ACCESS  read-only
		STATUS  mandatory       
		::= { dtiFddiSdbEntry 1 }

	dtiFddiPort	OBJECT-TYPE
		SYNTAX  INTEGER
		ACCESS  read-only
		STATUS  mandatory       
		::= { dtiFddiSdbEntry 2 }

	dtiFddiSdb	OBJECT-TYPE
		SYNTAX  INTEGER
		ACCESS  read-only
		STATUS  mandatory       
		::= { dtiFddiSdbEntry 3 }

	dtiFddiSdbCcnt     OBJECT-TYPE
		SYNTAX  Counter64
		ACCESS  read-only
		STATUS  mandatory       
		::= { dtiFddiSdbEntry  4 }

	dtiFddiSdbRmin     OBJECT-TYPE
		SYNTAX  Counter64
		ACCESS  read-only
		STATUS  mandatory       
		::= { dtiFddiSdbEntry  5 }

	dtiFddiSdbRmax     OBJECT-TYPE
		SYNTAX  Counter64
		ACCESS  read-only
		STATUS  mandatory       
		::= { dtiFddiSdbEntry  6 }

	dtiFddiSdbRcnt     OBJECT-TYPE
		SYNTAX  Counter64
		ACCESS  read-only
		STATUS  mandatory       
		::= { dtiFddiSdbEntry  7 }

	dtiFddiSdbRsmp     OBJECT-TYPE
		SYNTAX  Counter64
		ACCESS  read-only
		STATUS  mandatory       
		::= { dtiFddiSdbEntry  8 }

	END
