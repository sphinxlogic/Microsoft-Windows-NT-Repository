SRM-Alarm-MIB DEFINITIONS ::= BEGIN

--
-- Last Updated: June 30, 1995
--

IMPORTS
	enterprises, Counter, TimeTicks
		FROM RFC1155-SMI

	DisplayString
		FROM RFC1213-MIB

	TRAP-TYPE
		FROM RFC-1215

	OBJECT-TYPE
		FROM RFC-1212;


srm            OBJECT IDENTIFIER ::= { enterprises 787 }
srmTrap        OBJECT IDENTIFIER ::= { srm 1 }
srmtrapinfo    OBJECT IDENTIFIER ::= { srmTrap 100 }
rmGeneral      OBJECT IDENTIFIER ::= { srmTrap 30 }
rmCfgUpDn      OBJECT IDENTIFIER ::= { srmTrap 31 }


rmGeneric      OBJECT IDENTIFIER ::= { srmTrap 99 }
rmCisco        OBJECT IDENTIFIER ::= { srmTrap  1 }
rmWellfleet    OBJECT IDENTIFIER ::= { srmTrap  2 }
rm3COM         OBJECT IDENTIFIER ::= { srmTrap  3 }
rmMPR          OBJECT IDENTIFIER ::= { srmTrap  4 }
rmProt         OBJECT IDENTIFIER ::= { srmTrap  5 }
rmDEC          OBJECT IDENTIFIER ::= { srmTrap  6 }



-- ----------------------------------------------------------------------------
--
-- MIBII and Standards Based
--
-- ----------------------------------------------------------------------------

-- ----------------------------------------------------------------------------
--
-- IP Error Messages
--
-- ----------------------------------------------------------------------------
ipHeaderError       TRAP-TYPE
     ENTERPRISE     rmGeneric
     VARIABLES      { trapDescription }
     DESCRIPTION    "IP Header Error"
     --#TYPE        "IP Header Error"
     --#SUMMARY     "%s"
     --#ARGUMENTS   { 0 }
     --#SEVERITY    MINOR
     --#TIMEINDEX   1
     --#STATE       OPERATIONAL
     ::= 1

ipAddressError      TRAP-TYPE
     ENTERPRISE     rmGeneric
     VARIABLES      { trapDescription }
     DESCRIPTION    "IP Address Error"
     --#TYPE        "IP Address Error"
     --#SUMMARY     "%s"
     --#ARGUMENTS   { 0 }
     --#SEVERITY    MINOR
     --#TIMEINDEX   1
     --#STATE       OPERATIONAL
     ::= 2

ipUnknownProtocol   TRAP-TYPE
     ENTERPRISE     rmGeneric
     VARIABLES      { trapDescription }
     DESCRIPTION    "IP Unknown Protocol"
     --#TYPE        "IP Unknown Protocol"
     --#SUMMARY     "%s"
     --#ARGUMENTS   { 0 }
     --#SEVERITY    WARNING
     --#TIMEINDEX   1
     --#STATE       OPERATIONAL
     ::= 3

ipInDiscardError    TRAP-TYPE
     ENTERPRISE     rmGeneric
     VARIABLES      { trapDescription }
     DESCRIPTION    "IP Input Discard Error"
     --#TYPE        "IP Input Discard Error"
     --#SUMMARY     "%s"
     --#ARGUMENTS   { 0 }
     --#SEVERITY    WARNING
     --#TIMEINDEX   1
     --#STATE       OPERATIONAL
     ::= 4

ipOutDiscardError   TRAP-TYPE
     ENTERPRISE     rmGeneric
     VARIABLES      { trapDescription }
     DESCRIPTION    "IP Output Discard Error"
     --#TYPE        "IP Output Discard Error"
     --#SUMMARY     "%s"
     --#ARGUMENTS   { 0 }
     --#SEVERITY    MAJOR
     --#TIMEINDEX   1
     --#STATE       OPERATIONAL
     ::= 5

ipNoRoute           TRAP-TYPE
     ENTERPRISE     rmGeneric
     VARIABLES      { trapDescription }
     DESCRIPTION    "IP No Route To Destination"
     --#TYPE        "IP No Route To Destination"
     --#SUMMARY     "%s"
     --#ARGUMENTS   { 0 }
     --#SEVERITY    MINOR
     --#TIMEINDEX   1
     --#STATE       OPERATIONAL
     ::= 6

ipFragmentError     TRAP-TYPE
     ENTERPRISE     rmGeneric
     VARIABLES      { trapDescription }
     DESCRIPTION    "IP Fragmentation Error"
     --#TYPE        "IP Fragmentation Error"
     --#SUMMARY     "%s"
     --#ARGUMENTS   { 0 }
     --#SEVERITY    MINOR
     --#TIMEINDEX   1
     --#STATE       OPERATIONAL
     ::= 7

ipReassemblyError   TRAP-TYPE
     ENTERPRISE     rmGeneric
     VARIABLES      { trapDescription }
     DESCRIPTION    "IP Reassembly Error"
     --#TYPE        "IP Reassembly Error"
     --#SUMMARY     "%s"
     --#ARGUMENTS   { 0 }
     --#SEVERITY    MINOR
     --#TIMEINDEX   1
     --#STATE       OPERATIONAL
     ::= 8

-- ----------------------------------------------------------------------------
--
-- AppleTalk Error Messages
--
-- ----------------------------------------------------------------------------
appNoRoute          TRAP-TYPE
     ENTERPRISE     rmGeneric
     VARIABLES      { trapDescription }
     DESCRIPTION    "Appletalk No Route To Destination"
     --#TYPE        "Appletalk No Route To Destination"
     --#SUMMARY     "%s"
     --#ARGUMENTS   { 0 }
     --#SEVERITY    MINOR
     --#TIMEINDEX   1
     --#STATE       OPERATIONAL
     ::= 9

appTooShort         TRAP-TYPE
     ENTERPRISE     rmGeneric
     VARIABLES      { trapDescription }
     DESCRIPTION    "Appletalk Data Length Too Short"
     --#TYPE        "Appletalk Data Length Too Short"
     --#SUMMARY     "%s"
     --#ARGUMENTS   { 0 }
     --#SEVERITY    MINOR
     --#TIMEINDEX   1
     --#STATE       OPERATIONAL
     ::= 10

appTooLong          TRAP-TYPE
     ENTERPRISE     rmGeneric
     VARIABLES      { trapDescription }
     DESCRIPTION    "Appletalk Data Length Too Long"
     --#TYPE        "Appletalk Data Length Too Long"
     --#SUMMARY     "%s"
     --#ARGUMENTS   { 0 }
     --#SEVERITY    MINOR
     --#TIMEINDEX   1
     --#STATE       OPERATIONAL
     ::= 11

appBroadcast        TRAP-TYPE
     ENTERPRISE     rmGeneric
     VARIABLES      { trapDescription }
     DESCRIPTION    "Appletalk Broadcast No Access to Destination"
     --#TYPE        "Appletalk Broadcast No Access to Destination"
     --#SUMMARY     "%s"
     --#ARGUMENTS   { 0 }
     --#SEVERITY    MINOR
     --#TIMEINDEX   1
     --#STATE       OPERATIONAL
     ::= 12

appNoAccess         TRAP-TYPE
     ENTERPRISE     rmGeneric
     VARIABLES      { trapDescription }
     DESCRIPTION    "Appletalk No Access to Destination"
     --#TYPE        "Appletalk No Access to Destination"
     --#SUMMARY     "%s"
     --#ARGUMENTS   { 0 }
     --#SEVERITY    MINOR
     --#TIMEINDEX   1
     --#STATE       OPERATIONAL
     ::= 13

appNotGate          TRAP-TYPE
     ENTERPRISE     rmGeneric
     VARIABLES      { trapDescription }
     DESCRIPTION    "Appletalk Not Gateway To Destination"
     --#TYPE        "Appletalk Not Gateway To Destination"
     --#SUMMARY     "%s"
     --#ARGUMENTS   { 0 }
     --#SEVERITY    MINOR
     --#TIMEINDEX   1
     --#STATE       OPERATIONAL
     ::= 14

appChecksumError    TRAP-TYPE
     ENTERPRISE     rmGeneric
     VARIABLES      { trapDescription }
     DESCRIPTION    "Appletalk Checksum Error"
     --#TYPE        "Appletalk Checksum Error"
     --#SUMMARY     "%s"
     --#ARGUMENTS   { 0 }
     --#SEVERITY    MINOR
     --#TIMEINDEX   1
     --#STATE       OPERATIONAL
     ::= 15

appFailedEncap      TRAP-TYPE
     ENTERPRISE     rmGeneric
     VARIABLES      { trapDescription }
     DESCRIPTION    "Appletalk Failed Encapsulation"
     --#TYPE        "Appletalk Failed Encapsulation"
     --#SUMMARY     "%s"
     --#ARGUMENTS   { 0 }
     --#SEVERITY    MINOR
     --#TIMEINDEX   1
     --#STATE       OPERATIONAL
     ::= 16

appUnknownProtocol  TRAP-TYPE
     ENTERPRISE     rmGeneric
     VARIABLES      { trapDescription }
     DESCRIPTION    "Appletalk Unknown Protocol"
     --#TYPE        "Appletalk Unknown Protocol"
     --#SUMMARY     "%s"
     --#ARGUMENTS   { 0 }
     --#SEVERITY    MINOR
     --#TIMEINDEX   1
     --#STATE       OPERATIONAL
     ::= 17

appPacketDiscarded  TRAP-TYPE
     ENTERPRISE     rmGeneric
     VARIABLES      { trapDescription }
     DESCRIPTION    "Appletalk Packet Discarded"
     --#TYPE        "Appletalk Packet Discarded"
     --#SUMMARY     "%s"
     --#ARGUMENTS   { 0 }
     --#SEVERITY    MINOR
     --#TIMEINDEX   1
     --#STATE       OPERATIONAL
     ::= 18

appHopCountError    TRAP-TYPE
     ENTERPRISE     rmGeneric
     VARIABLES      { trapDescription }
     DESCRIPTION    "Appletalk Hopcount Exceeded"
     --#TYPE        "Appletalk Hopcount Exceeded"
     --#SUMMARY     "%s"
     --#ARGUMENTS   { 0 }
     --#SEVERITY    MINOR
     --#TIMEINDEX   1
     --#STATE       OPERATIONAL
     ::= 19

appHeaderError      TRAP-TYPE
     ENTERPRISE     rmGeneric
     VARIABLES      { trapDescription }
     DESCRIPTION    "Appletalk Header Error"
     --#TYPE        "Appletalk Header Error"
     --#SUMMARY     "%s"
     --#ARGUMENTS   { 0 }
     --#SEVERITY    MINOR
     --#TIMEINDEX   1
     --#STATE       OPERATIONAL
     ::= 20

-- ----------------------------------------------------------------------------
--
-- IPX Error Messages
--
-- ----------------------------------------------------------------------------
ipxChecksumError    TRAP-TYPE
     ENTERPRISE     rmGeneric
     VARIABLES      { trapDescription }
     DESCRIPTION    "IPX Checksum Errors"
     --#TYPE        "IPX Checksum Errors"
     --#SUMMARY     "%s"
     --#ARGUMENTS   { 0 }
     --#SEVERITY    WARNING
     --#TIMEINDEX   1
     --#STATE       OPERATIONAL
     ::= 21

ipxHopCountError    TRAP-TYPE
     ENTERPRISE     rmGeneric
     VARIABLES      { trapDescription }
     DESCRIPTION    "IPX Hopcount Exceeded"
     --#TYPE        "IPX Hopcount Exceeded"
     --#SUMMARY     "%s"
     --#ARGUMENTS   { 0 }
     --#SEVERITY    MAJOR
     --#TIMEINDEX   1
     --#STATE       OPERATIONAL
     ::= 22

ipxNoRoute          TRAP-TYPE
     ENTERPRISE     rmGeneric
     VARIABLES      { trapDescription }
     DESCRIPTION    "IPX No Route To Destination"
     --#TYPE        "IPX No Route To Destination"
     --#SUMMARY     "%s"
     --#ARGUMENTS   { 0 }
     --#SEVERITY    MAJOR
     --#TIMEINDEX   1
     --#STATE       OPERATIONAL
     ::= 23

ipxFailedEncaps     TRAP-TYPE
     ENTERPRISE     rmGeneric
     VARIABLES      { trapDescription }
     DESCRIPTION    "IPX Failed Encapsulation"
     --#TYPE        "IPX Failed Encapsulation"
     --#SUMMARY     "%s"
     --#ARGUMENTS   { 0 }
     --#SEVERITY    MAJOR
     --#TIMEINDEX   1
     --#STATE       OPERATIONAL
     ::= 24

ipxUnknownProtocol  TRAP-TYPE
     ENTERPRISE     rmGeneric
     VARIABLES      { trapDescription }
     DESCRIPTION    "IPX Unknown Protocol"
     --#TYPE        "IPX Unknown Protocol"
     --#SUMMARY     "%s"
     --#ARGUMENTS   { 0 }
     --#SEVERITY    WARNING
     --#TIMEINDEX   1
     --#STATE       OPERATIONAL
     ::= 25

ipxHeaderError    TRAP-TYPE
     ENTERPRISE     rmGeneric
     VARIABLES      { trapDescription }
     DESCRIPTION    "IPX Header Error"
     --#TYPE        "IPX Header Error"
     --#SUMMARY     "%s"
     --#ARGUMENTS   { 0 }
     --#SEVERITY    MINOR
     --#TIMEINDEX   1
     --#STATE       OPERATIONAL
     ::= 26

ipxSocketNotOpen    TRAP-TYPE
     ENTERPRISE     rmGeneric
     VARIABLES      { trapDescription }
     DESCRIPTION    "IPX Socket Not Open"
     --#TYPE        "IPX Socket Not Open"
     --#SUMMARY     "%s"
     --#ARGUMENTS   { 0 }
     --#SEVERITY    MAJOR
     --#TIMEINDEX   1
     --#STATE       OPERATIONAL
     ::= 27

ipxAddressError     TRAP-TYPE
     ENTERPRISE     rmGeneric
     VARIABLES      { trapDescription }
     DESCRIPTION    "IPX Address Error"
     --#TYPE        "IPX Address Error"
     --#SUMMARY     "%s"
     --#ARGUMENTS   { 0 }
     --#SEVERITY    WARNING
     --#TIMEINDEX   1
     --#STATE       OPERATIONAL
     ::= 28

ipxInDiscardError   TRAP-TYPE
     ENTERPRISE     rmGeneric
     VARIABLES      { trapDescription }
     DESCRIPTION    "IPX Input Discard Error"
     --#TYPE        "IPX Input Discard Error"
     --#SUMMARY     "%s"
     --#ARGUMENTS   { 0 }
     --#SEVERITY    MAJOR
     --#TIMEINDEX   1
     --#STATE       OPERATIONAL
     ::= 29

ipxOutDiscardError  TRAP-TYPE
     ENTERPRISE     rmGeneric
     VARIABLES      { trapDescription }
     DESCRIPTION    "IPX Output Discard Error"
     --#TYPE        "IPX Output Discard Error"
     --#SUMMARY     "%s"
     --#ARGUMENTS   { 0 }
     --#SEVERITY    MAJOR
     --#TIMEINDEX   1
     --#STATE       OPERATIONAL
     ::= 30

-- ----------------------------------------------------------------------------
--
-- MIBII Interface Based
--
-- ----------------------------------------------------------------------------
ifInputDiscard      TRAP-TYPE
     ENTERPRISE     rmGeneric
     VARIABLES      { trapDescription }
     DESCRIPTION    "Interface Input Buffer Error"
     --#TYPE        "Interface Input Buffer Error"
     --#SUMMARY     "%s"
     --#ARGUMENTS   { 0 }
     --#SEVERITY    WARNING
     --#TIMEINDEX   1
     --#STATE       OPERATIONAL
     ::= 32

ifInputError        TRAP-TYPE
     ENTERPRISE     rmGeneric
     VARIABLES      { trapDescription }
     DESCRIPTION    "Interface Input Error"
     --#TYPE        "Interface Input Error"
     --#SUMMARY     "%s"
     --#ARGUMENTS   { 0 }
     --#SEVERITY    WARNING
     --#TIMEINDEX   1
     --#STATE       OPERATIONAL
     ::= 33

ifUnknownProtocol   TRAP-TYPE
     ENTERPRISE     rmGeneric
     VARIABLES      { trapDescription }
     DESCRIPTION    "Interface Unknown Protocol"
     --#TYPE        "Interface Unknown Protocol"
     --#SUMMARY     "%s"
     --#ARGUMENTS   { 0 }
     --#SEVERITY    WARNING
     --#TIMEINDEX   1
     --#STATE       OPERATIONAL
     ::= 34

ifOutputDiscard     TRAP-TYPE
     ENTERPRISE     rmGeneric
     VARIABLES      { trapDescription }
     DESCRIPTION    "Interface Output Buffer Error"
     --#TYPE        "Interface Output Buffer Error"
     --#SUMMARY     "%s"
     --#ARGUMENTS   { 0 }
     --#SEVERITY    WARNING
     --#TIMEINDEX   1
     --#STATE       OPERATIONAL
     ::= 35

ifGeneralOutError   TRAP-TYPE
     ENTERPRISE     rmGeneric
     VARIABLES      { trapDescription }
     DESCRIPTION    "Interface General Output Error"
     --#TYPE        "Interface General Output Error"
     --#SUMMARY     "%s"
     --#ARGUMENTS   { 0 }
     --#SEVERITY    WARNING
     --#TIMEINDEX   1
     --#STATE       OPERATIONAL
     ::= 36

-- ----------------------------------------------------------------------------
--
-- Ethernet
--
-- ----------------------------------------------------------------------------
ethAlignError       TRAP-TYPE
     ENTERPRISE     rmGeneric
     VARIABLES      { trapDescription }
     DESCRIPTION    "Ethernet Alignment Error"
     --#TYPE        "Ethernet Alignment Error"
     --#SUMMARY     "%s"
     --#ARGUMENTS   { 0 }
     --#SEVERITY    WARNING
     --#TIMEINDEX   1
     --#STATE       OPERATIONAL
     ::= 38

ethFCSError         TRAP-TYPE
     ENTERPRISE     rmGeneric
     VARIABLES      { trapDescription }
     DESCRIPTION    "Ethernet Frame Check Sequence Error"
     --#TYPE        "Ethernet Frame Check Sequence Error"
     --#SUMMARY     "%s"
     --#ARGUMENTS   { 0 }
     --#SEVERITY    WARNING
     --#TIMEINDEX   1
     --#STATE       OPERATIONAL
     ::= 39

ethSingleCollision  TRAP-TYPE
     ENTERPRISE     rmGeneric
     VARIABLES      { trapDescription }
     DESCRIPTION    "Ethernet Single Collision"
     --#TYPE        "Ethernet Single Collision"
     --#SUMMARY     "%s"
     --#ARGUMENTS   { 0 }
     --#SEVERITY    WARNING
     --#TIMEINDEX   1
     --#STATE       OPERATIONAL
     ::= 40

ethMultiplCollision TRAP-TYPE
     ENTERPRISE     rmGeneric
     VARIABLES      { trapDescription }
     DESCRIPTION    "Ethernet Multiple Collisions"
     --#TYPE        "Ethernet Multiple Collisions"
     --#SUMMARY     "%s"
     --#ARGUMENTS   { 0 }
     --#SEVERITY    WARNING
     --#TIMEINDEX   1
     --#STATE       OPERATIONAL
     ::= 41

ethSQETestError     TRAP-TYPE
     ENTERPRISE     rmGeneric
     VARIABLES      { trapDescription }
     DESCRIPTION    "Ethernet SQE Test Error"
     --#TYPE        "Ethernet SQE Test Error"
     --#SUMMARY     "%s"
     --#ARGUMENTS   { 0 }
     --#SEVERITY    MAJOR
     --#TIMEINDEX   1
     --#STATE       DEGRADED
     ::= 42

ethDeferXmit        TRAP-TYPE
     ENTERPRISE     rmGeneric
     VARIABLES      { trapDescription }
     DESCRIPTION    "Ethernet Deferred Transmission"
     --#TYPE        "Ethernet Deferred Transmission"
     --#SUMMARY     "%s"
     --#ARGUMENTS   { 0 }
     --#SEVERITY    MINOR
     --#TIMEINDEX   1
     --#STATE       OPERATIONAL
     ::= 43

ethLateCollsion     TRAP-TYPE
     ENTERPRISE     rmGeneric
     VARIABLES      { trapDescription }
     DESCRIPTION    "Ethernet Late Collisions"
     --#TYPE        "Ethernet Late Collisions"
     --#SUMMARY     "%s"
     --#ARGUMENTS   { 0 }
     --#SEVERITY    WARNING
     --#TIMEINDEX   1
     --#STATE       OPERATIONAL
     ::= 44

ethExsCollision     TRAP-TYPE
     ENTERPRISE     rmGeneric
     VARIABLES      { trapDescription }
     DESCRIPTION    "Ethernet Excessive Collisions"
     --#TYPE        "Ethernet Excessive Collisions"
     --#SUMMARY     "%s"
     --#ARGUMENTS   { 0 }
     --#SEVERITY    MAJOR
     --#TIMEINDEX   1
     --#STATE       DEGRADED
     ::= 45

ethIntMACXmitError  TRAP-TYPE
     ENTERPRISE     rmGeneric
     VARIABLES      { trapDescription }
     DESCRIPTION    "Ethernet Internal MAC Transmit Error"
     --#TYPE        "Ethernet Internal MAC Transmit Error"
     --#SUMMARY     "%s"
     --#ARGUMENTS   { 0 }
     --#SEVERITY    WARNING
     --#TIMEINDEX   1
     --#STATE       OPERATIONAL
     ::= 46

ethCarierSenseError TRAP-TYPE
     ENTERPRISE     rmGeneric
     VARIABLES      { trapDescription }
     DESCRIPTION    "Ethernet Carrier Sense Error"
     --#TYPE        "Ethernet Carrier Sense Error"
     --#SUMMARY     "%s"
     --#ARGUMENTS   { 0 }
     --#SEVERITY    WARNING
     --#TIMEINDEX   1
     --#STATE       OPERATIONAL
     ::= 47

ethExsDeferals      TRAP-TYPE
     ENTERPRISE     rmGeneric
     VARIABLES      { trapDescription }
     DESCRIPTION    "Ethernet Excessive Deferrals"
     --#TYPE        "Ethernet Excessive Deferrals"
     --#SUMMARY     "%s"
     --#ARGUMENTS   { 0 }
     --#SEVERITY    DEGRADED
     --#TIMEINDEX   1
     --#STATE       MAJOR
     ::= 48

ethFrameTooLong     TRAP-TYPE
     ENTERPRISE     rmGeneric
     VARIABLES      { trapDescription }
     DESCRIPTION    "Ethernet Frame Too Long"
     --#TYPE        "Ethernet Frame Too Long"
     --#SUMMARY     "%s"
     --#ARGUMENTS   { 0 }
     --#SEVERITY    WARNING
     --#TIMEINDEX   1
     --#STATE       OPERATIONAL
     ::= 49

ethInRangeLength    TRAP-TYPE
     ENTERPRISE     rmGeneric
     VARIABLES      { trapDescription }
     DESCRIPTION    "Ethernet In Range Length"
     --#TYPE        "Ethernet In Range Length"
     --#SUMMARY     "%s"
     --#ARGUMENTS   { 0 }
     --#SEVERITY    WARNING
     --#TIMEINDEX   1
     --#STATE       OPERATIONAL
     ::= 50

ethOutRangeLength   TRAP-TYPE
     ENTERPRISE     rmGeneric
     VARIABLES      { trapDescription }
     DESCRIPTION    "Ethernet Out Of Range Length Field"
     --#TYPE        "Ethernet Out Of Range Length Field"
     --#SUMMARY     "%s"
     --#ARGUMENTS   { 0 }
     --#SEVERITY    WARNING
     --#TIMEINDEX   1
     --#STATE       OPERATIONAL
     ::= 51

ethIntMACRcvError   TRAP-TYPE
     ENTERPRISE     rmGeneric
     VARIABLES      { trapDescription }
     DESCRIPTION    "Ethernet Internal MAC Receive Error"
     --#TYPE        "Ethernet Internal MAC Receive Error"
     --#SUMMARY     "%s"
     --#ARGUMENTS   { 0 }
     --#SEVERITY    WARNING
     --#TIMEINDEX   1
     --#STATE       OPERATIONAL
     ::= 52

-- ----------------------------------------------------------------------------
--
-- Token Ring
--
-- ----------------------------------------------------------------------------
tokLineError        TRAP-TYPE
     ENTERPRISE     rmGeneric
     VARIABLES      { trapDescription }
     DESCRIPTION    "Token Ring Line Error"
     --#TYPE        "Token Ring Line Error"
     --#SUMMARY     "%s"
     --#ARGUMENTS   { 0 }
     --#SEVERITY    WARNING
     --#TIMEINDEX   1
     --#STATE       OPERATIONAL
     ::= 54

tokBurstError       TRAP-TYPE
     ENTERPRISE     rmGeneric
     VARIABLES      { trapDescription }
     DESCRIPTION    "Token Ring Burst Error"
     --#TYPE        "Token Ring Burst Error"
     --#SUMMARY     "%s"
     --#ARGUMENTS   { 0 }
     --#SEVERITY    WARNING
     --#TIMEINDEX   1
     --#STATE       OPERATIONAL
     ::= 55

tokACError          TRAP-TYPE
     ENTERPRISE     rmGeneric
     VARIABLES      { trapDescription }
     DESCRIPTION    "Token Ring AC Error"
     --#TYPE        "Token Ring AC Error"
     --#SUMMARY     "%s"
     --#ARGUMENTS   { 0 }
     --#SEVERITY    WARNING
     --#TIMEINDEX   1
     --#STATE       OPERATIONAL
     ::= 56

tokAbortTransmit    TRAP-TYPE
     ENTERPRISE     rmGeneric
     VARIABLES      { trapDescription }
     DESCRIPTION    "Token Ring Abort Transmit"
     --#TYPE        "Token Ring Abort Transmit"
     --#SUMMARY     "%s"
     --#ARGUMENTS   { 0 }
     --#SEVERITY    WARNING
     --#TIMEINDEX   1
     --#STATE       OPERATIONAL
     ::= 57

tokInternalError    TRAP-TYPE
     ENTERPRISE     rmGeneric
     VARIABLES      { trapDescription }
     DESCRIPTION    "Token Ring Internal Error"
     --#TYPE        "Token Ring Internal Error"
     --#SUMMARY     "%s"
     --#ARGUMENTS   { 0 }
     --#SEVERITY    WARNING
     --#TIMEINDEX   1
     --#STATE       OPERATIONAL
     ::= 58

tokLostFrameError   TRAP-TYPE
     ENTERPRISE     rmGeneric
     VARIABLES      { trapDescription }
     DESCRIPTION    "Token Ring Lost Frame Error"
     --#TYPE        "Token Ring Lost Frame Error"
     --#SUMMARY     "%s"
     --#ARGUMENTS   { 0 }
     --#SEVERITY    WARNING
     --#TIMEINDEX   1
     --#STATE       OPERATIONAL
     ::= 59

tokReceiveCongest   TRAP-TYPE
     ENTERPRISE     rmGeneric
     VARIABLES      { trapDescription }
     DESCRIPTION    "Token Ring Receive Congestion"
     --#TYPE        "Token Ring Recieve Congestion"
     --#SUMMARY     "%s"
     --#ARGUMENTS   { 0 }
     --#SEVERITY    WARNING
     --#TIMEINDEX   1
     --#STATE       OPERATIONAL
     ::= 60

tokFrameCopyError   TRAP-TYPE
     ENTERPRISE     rmGeneric
     VARIABLES      { trapDescription }
     DESCRIPTION    "Token Ring Frame Copy Error"
     --#TYPE        "Token Ring Frame Copy Error"
     --#SUMMARY     "%s"
     --#ARGUMENTS   { 0 }
     --#SEVERITY    WARNING
     --#TIMEINDEX   1
     --#STATE       OPERATIONAL
     ::= 61

tokTokenError       TRAP-TYPE
     ENTERPRISE     rmGeneric
     VARIABLES      { trapDescription }
     DESCRIPTION    "Token Ring Token Error"
     --#TYPE        "Token Ring Token Error"
     --#SUMMARY     "%s"
     --#ARGUMENTS   { 0 }
     --#SEVERITY    WARNING
     --#TIMEINDEX   1
     --#STATE       OPERATIONAL
     ::= 62

tokSoftError        TRAP-TYPE
     ENTERPRISE     rmGeneric
     VARIABLES      { trapDescription }
     DESCRIPTION    "Token Ring Soft Error"
     --#TYPE        "Token Ring Soft Error"
     --#SUMMARY     "%s"
     --#ARGUMENTS   { 0 }
     --#SEVERITY    WARNING
     --#TIMEINDEX   1
     --#STATE       OPERATIONAL
     ::= 63

tokHardError        TRAP-TYPE
     ENTERPRISE     rmGeneric
     VARIABLES      { trapDescription }
     DESCRIPTION    "Token Ring Hard Error"
     --#TYPE        "Token Ring Hard Error"
     --#SUMMARY     "%s"
     --#ARGUMENTS   { 0 }
     --#SEVERITY    WARNING
     --#TIMEINDEX   1
     --#STATE       OPERATIONAL
     ::= 64

tokSignalLoss       TRAP-TYPE
     ENTERPRISE     rmGeneric
     VARIABLES      { trapDescription }
     DESCRIPTION    "Token Ring Signal Loss"
     --#TYPE        "Token Ring Signal Loss"
     --#SUMMARY     "%s"
     --#ARGUMENTS   { 0 }
     --#SEVERITY    DEGRADED
     --#TIMEINDEX   1
     --#STATE       MAJOR
     ::= 65

tokTranmitBeacon    TRAP-TYPE
     ENTERPRISE     rmGeneric
     VARIABLES      { trapDescription }
     DESCRIPTION    "Token Ring Transmit Beacon"
     --#TYPE        "Token Ring Transmit Beacon"
     --#SUMMARY     "%s"
     --#ARGUMENTS   { 0 }
     --#SEVERITY    WARNING
     --#TIMEINDEX   1
     --#STATE       OPERATIONAL
     ::= 66

tokRecovery         TRAP-TYPE
     ENTERPRISE     rmGeneric
     VARIABLES      { trapDescription }
     DESCRIPTION    "Token Ring Recovery"
     --#TYPE        "Token Ring Recovery"
     --#SUMMARY     "%s"
     --#ARGUMENTS   { 0 }
     --#SEVERITY    WARNING
     --#TIMEINDEX   1
     --#STATE       OPERATIONAL
     ::= 67

tokLobeWire         TRAP-TYPE
     ENTERPRISE     rmGeneric
     VARIABLES      { trapDescription }
     DESCRIPTION    "Token Ring Lobe Wire"
     --#TYPE        "Token Ring Lobe Wire"
     --#SUMMARY     "%s"
     --#ARGUMENTS   { 0 }
     --#SEVERITY    MAJOR
     --#TIMEINDEX   1
     --#STATE       DEGRADED
     ::= 68

tokRemove           TRAP-TYPE
     ENTERPRISE     rmGeneric
     VARIABLES      { trapDescription }
     DESCRIPTION    "Token Ring Internal MAC Receive Error"
     --#TYPE        "Token Ring Internal MAC Receive Error"
     --#SUMMARY     "%s"
     --#ARGUMENTS   { 0 }
     --#SEVERITY    MAJOR
     --#TIMEINDEX   1
     --#STATE       DEGRADED
     ::= 69

tokSingleStation    TRAP-TYPE
     ENTERPRISE     rmGeneric
     VARIABLES      { trapDescription }
     DESCRIPTION    "Token Ring Single Station"
     --#TYPE        "Token Ring Single Station"
     --#SUMMARY     "%s"
     --#ARGUMENTS   { 0 }
     --#SEVERITY    MAJOR
     --#TIMEINDEX   1
     --#STATE       DEGRADED
     ::= 70

tokFrequencyError   TRAP-TYPE
     ENTERPRISE     rmGeneric
     VARIABLES      { trapDescription }
     DESCRIPTION    "Token Ring Frequency Error"
     --#TYPE        "Token Ring Frequency Error"
     --#SUMMARY     "%s"
     --#ARGUMENTS   { 0 }
     --#SEVERITY    MAJOR
     --#TIMEINDEX   1
     --#STATE       DEGRADED
     ::= 71

-- ----------------------------------------------------------------------------
--
-- Bridging
--
-- ----------------------------------------------------------------------------
brgSegMisDiscard    TRAP-TYPE
     ENTERPRISE     rmGeneric
     VARIABLES      { trapDescription }
     DESCRIPTION    "SRB Segment Mismatch Discard"
     --#TYPE        "SRB Segment Mismatch Discard"
     --#SUMMARY     "%s"
     --#ARGUMENTS   { 0 }
     --#SEVERITY    WARNING
     --#TIMEINDEX   1
     --#STATE       OPERATIONAL
     ::= 73

brgDupSegDiscard    TRAP-TYPE
     ENTERPRISE     rmGeneric
     VARIABLES      { trapDescription }
     DESCRIPTION    "SRB Duplicate Segment Discard"
     --#TYPE        "SRB Duplicate Segment Discard"
     --#SUMMARY     "%s"
     --#ARGUMENTS   { 0 }
     --#SEVERITY    WARNING
     --#TIMEINDEX   1
     --#STATE       OPERATIONAL
     ::= 74

brgHopExceedDiscard TRAP-TYPE
     ENTERPRISE     rmGeneric
     VARIABLES      { trapDescription }
     DESCRIPTION    "SRB Hop Count Exceded Discard"
     --#TYPE        "SRB Hop Count Exceded Discard"
     --#SUMMARY     "%s"
     --#ARGUMENTS   { 0 }
     --#SEVERITY    WARNING
     --#TIMEINDEX   1
     --#STATE       OPERATIONAL
     ::= 75

brgSTPDelayExceed   TRAP-TYPE
     ENTERPRISE     rmGeneric
     VARIABLES      { trapDescription }
     DESCRIPTION    "STP Abort Exceeds"
     --#TYPE        "STP Delay Exceeds"
     --#SUMMARY     "%s"
     --#ARGUMENTS   { 0 }
     --#SEVERITY    WARNING
     --#TIMEINDEX   1
     --#STATE       OPERATIONAL
     ::= 77

brgSTPMTUExceed     TRAP-TYPE
     ENTERPRISE     rmGeneric
     VARIABLES      { trapDescription }
     DESCRIPTION    "STP MTU Delay Exceeds"
     --#TYPE        "STP MTU Delay Exceeds"
     --#SUMMARY     "%s"
     --#ARGUMENTS   { 0 }
     --#SEVERITY    WARNING
     --#TIMEINDEX   1
     --#STATE       OPERATIONAL
     ::= 78

brgSRBDupLanTree    TRAP-TYPE
     ENTERPRISE     rmGeneric
     VARIABLES      { trapDescription }
     DESCRIPTION    "SRB Duplication Error"
     --#TYPE        "SRB Duplication Error"
     --#SUMMARY     "%s"
     --#ARGUMENTS   { 0 }
     --#SEVERITY    WARNING
     --#TIMEINDEX   1
     --#STATE       OPERATIONAL
     ::= 79

brgLanIDMismatch    TRAP-TYPE
     ENTERPRISE     rmGeneric
     VARIABLES      { trapDescription }
     DESCRIPTION    "SRB Port Mismatch"
     --#TYPE        "SRB Port Mismatch"
     --#SUMMARY     "%s"
     --#ARGUMENTS   { 0 }
     --#SEVERITY    WARNING
     --#TIMEINDEX   1
     --#STATE       OPERATIONAL
     ::= 80

-- ----------------------------------------------------------------------------
--
-- FDDI
--
-- ----------------------------------------------------------------------------
fibGeneralError     TRAP-TYPE
     ENTERPRISE     rmGeneric
     VARIABLES      { trapDescription }
     DESCRIPTION    "FDDI General Error"
     --#TYPE        "FDDI General Error"
     --#SUMMARY     "%s"
     --#ARGUMENTS   { 0 }
     --#SEVERITY    WARNING
     --#TIMEINDEX   1
     --#STATE       OPERATIONAL
     ::= 82

fibLostFrame        TRAP-TYPE
     ENTERPRISE     rmGeneric
     VARIABLES      { trapDescription }
     DESCRIPTION    "FDDI Lost Frame"
     --#TYPE        "FDDI Lost Frame"
     --#SUMMARY     "%s"
     --#ARGUMENTS   { 0 }
     --#SEVERITY    WARNING
     --#TIMEINDEX   1
     --#STATE       OPERATIONAL
     ::= 83

-- ----------------------------------------------------------------------------
--
-- Router Specific Data
-- Please Note - Numbers Overlap Between Vendors !!!
--
-- ----------------------------------------------------------------------------

-- ----------------------------------------------------------------------------
--
-- Cisco
--
-- ----------------------------------------------------------------------------
cifInputOverrun     TRAP-TYPE
     ENTERPRISE     rmCisco
     VARIABLES      { trapDescription }
     DESCRIPTION    "Input Overrun"
     --#TYPE        "Input Overrun"
     --#SUMMARY     "%s"
     --#ARGUMENTS   { 0 }
     --#SEVERITY    MINOR
     --#TIMEINDEX   1
     --#STATE       OPERATIONAL
     ::= 85

cifInputAbort       TRAP-TYPE
     ENTERPRISE     rmCisco
     VARIABLES      { trapDescription }
     DESCRIPTION    "Input Abort"
     --#TYPE        "Input Abort"
     --#SUMMARY     "%s"
     --#ARGUMENTS   { 0 }
     --#SEVERITY    MINOR
     --#TIMEINDEX   1
     --#STATE       OPERATIONAL
     ::= 86

cifCarrierTransition TRAP-TYPE
     ENTERPRISE     rmCisco
     VARIABLES      { trapDescription }
     DESCRIPTION    "Carrier Signal Transition"
     --#TYPE        "Carrier Signal Transition"
     --#SUMMARY     "%s"
     --#ARGUMENTS   { 0 }
     --#SEVERITY    MINOR
     --#TIMEINDEX   1
     --#STATE       OPERATIONAL
     ::= 87

cifCollision        TRAP-TYPE
     ENTERPRISE     rmCisco
     VARIABLES      { trapDescription }
     DESCRIPTION    "Output Collision"
     --#TYPE        "Output Collision"
     --#SUMMARY     "%s"
     --#ARGUMENTS   { 0 }
     --#SEVERITY    MINOR
     --#TIMEINDEX   1
     --#STATE       OPERATIONAL
     ::= 88

cifInputQueueDrop   TRAP-TYPE
     ENTERPRISE     rmCisco
     VARIABLES      { trapDescription }
     DESCRIPTION    "Input Queue Drop"
     --#TYPE        "Input Queue Drop"
     --#SUMMARY     "%s"
     --#ARGUMENTS   { 0 }
     --#SEVERITY    WARNING
     --#TIMEINDEX   1
     --#STATE       OPERATIONAL
     ::= 89

cifOutputQueueDrop  TRAP-TYPE
     ENTERPRISE     rmCisco
     VARIABLES      { trapDescription }
     DESCRIPTION    "Output Queue Drop"
     --#TYPE        "Output Queue Drop"
     --#SUMMARY     "%s"
     --#ARGUMENTS   { 0 }
     --#SEVERITY    WARNING
     --#TIMEINDEX   1
     --#STATE       OPERATIONAL
     ::= 90

-- ----------------------------------------------------------------------------
--
-- Wellfleet
--
-- ----------------------------------------------------------------------------
-- Wellfellet IPX
wipxHeaderError     TRAP-TYPE
     ENTERPRISE     rmWellfleet
     VARIABLES      { trapDescription }
     DESCRIPTION    "IPX Header Error"
     --#TYPE        "IPX Header Error"
     --#SUMMARY     "%s"
     --#ARGUMENTS   { 0 }
     --#SEVERITY    MINOR
     --#TIMEINDEX   1
     --#STATE       OPERATIONAL
     ::= 86

wipxAddressError    TRAP-TYPE
     ENTERPRISE     rmWellfleet
     VARIABLES      { trapDescription }
     DESCRIPTION    "IPX Address Error"
     --#TYPE        "IPX Address Error"
     --#SUMMARY     "%s"
     --#ARGUMENTS   { 0 }
     --#SEVERITY    MINOR
     --#TIMEINDEX   1
     --#STATE       OPERATIONAL
     ::= 87

wipxUnknownProtocol TRAP-TYPE
     ENTERPRISE     rmWellfleet
     VARIABLES      { trapDescription }
     DESCRIPTION    "IPX Unknown Protocol"
     --#TYPE        "IPX Unknown Protocol"
     --#SUMMARY     "%s"
     --#ARGUMENTS   { 0 }
     --#SEVERITY    WARNING
     --#TIMEINDEX   1
     --#STATE       OPERATIONAL
     ::= 88

wipxInDiscardError  TRAP-TYPE
     ENTERPRISE     rmWellfleet
     VARIABLES      { trapDescription }
     DESCRIPTION    "IPX In Discard Error"
     --#TYPE        "IPX In Discard Error"
     --#SUMMARY     "%s"
     --#ARGUMENTS   { 0 }
     --#SEVERITY    MINOR
     --#TIMEINDEX   1
     --#STATE       OPERATIONAL
     ::= 89

wipxOutDiscardError TRAP-TYPE
     ENTERPRISE     rmWellfleet
     VARIABLES      { trapDescription }
     DESCRIPTION    "IPX Output Discard Error"
     --#TYPE        "IPX Output Discard Error"
     --#SUMMARY     "%s"
     --#ARGUMENTS   { 0 }
     --#SEVERITY    MINOR
     --#TIMEINDEX   1
     --#STATE       OPERATIONAL
     ::= 90

wipxNoRoute         TRAP-TYPE
     ENTERPRISE     rmWellfleet
     VARIABLES      { trapDescription }
     DESCRIPTION    "IPX No Route To Destination"
     --#TYPE        "IPX No Route To Destination"
     --#SUMMARY     "%s"
     --#ARGUMENTS   { 0 }
     --#SEVERITY    MINOR
     --#TIMEINDEX   1
     --#STATE       OPERATIONAL
     ::= 91

-- Wellfleet AppleTalk
wappHeaderError     TRAP-TYPE
     ENTERPRISE     rmWellfleet
     VARIABLES      { trapDescription }
     DESCRIPTION    "AppleTalk Header Error"
     --#TYPE        "AppleTalk Header Error"
     --#SUMMARY     "%s"
     --#ARGUMENTS   { 0 }
     --#SEVERITY    MINOR
     --#TIMEINDEX   1
     --#STATE       OPERATIONAL
     ::= 93

wappUnknownProtocol TRAP-TYPE
     ENTERPRISE     rmWellfleet
     VARIABLES      { trapDescription }
     DESCRIPTION    "AppleTalk Unknown Protocol"
     --#TYPE        "AppleTalk Unknown Protocol"
     --#SUMMARY     "%s"
     --#ARGUMENTS   { 0 }
     --#SEVERITY    MINOR
     --#TIMEINDEX   1
     --#STATE       OPERATIONAL
     ::= 94

wappChecksumError   TRAP-TYPE
     ENTERPRISE     rmWellfleet
     VARIABLES      { trapDescription }
     DESCRIPTION    "AppleTalk Checksum Error"
     --#TYPE        "AppleTalk Checksum Error"
     --#SUMMARY     "%s"
     --#ARGUMENTS   { 0 }
     --#SEVERITY    WARNING
     --#TIMEINDEX   1
     --#STATE       OPERATIONAL
     ::= 95

wappNoRoute         TRAP-TYPE
     ENTERPRISE     rmWellfleet
     VARIABLES      { trapDescription }
     DESCRIPTION    "AppleTalk No Route To Destination"
     --#TYPE        "AppleTalk No Route To Destination"
     --#SUMMARY     "%s"
     --#ARGUMENTS   { 0 }
     --#SEVERITY    MINOR
     --#TIMEINDEX   1
     --#STATE       OPERATIONAL
     ::= 96

wappBroadcastNoAcc  TRAP-TYPE
     ENTERPRISE     rmWellfleet
     VARIABLES      { trapDescription }
     DESCRIPTION    "AppleTalk Broadcast No Access To Destination"
     --#TYPE        "AppleTalk Broadcast No Access To Destination"
     --#SUMMARY     "%s"
     --#ARGUMENTS   { 0 }
     --#SEVERITY    MINOR
     --#TIMEINDEX   1
     --#STATE       OPERATIONAL
     ::= 97

wappHopcountError   TRAP-TYPE
     ENTERPRISE     rmWellfleet
     VARIABLES      { trapDescription }
     DESCRIPTION    "AppleTalk Hopcount Exceeded"
     --#TYPE        "AppleTalk Hopcount Exceeded"
     --#SUMMARY     "%s"
     --#ARGUMENTS   { 0 }
     --#SEVERITY    MINOR
     --#TIMEINDEX   1
     --#STATE       OPERATIONAL
     ::= 98

-- Wellfleet IP
wipHeaderError      TRAP-TYPE
     ENTERPRISE     rmWellfleet
     VARIABLES      { trapDescription }
     DESCRIPTION    "IP Header Error"
     --#TYPE        "IP Header Error"
     --#SUMMARY     "%s"
     --#ARGUMENTS   { 0 }
     --#SEVERITY    MINOR
     --#TIMEINDEX   1
     --#STATE       OPERATIONAL
     ::= 100

wipAddressError     TRAP-TYPE
     ENTERPRISE     rmWellfleet
     VARIABLES      { trapDescription }
     DESCRIPTION    "IP Address Error"
     --#TYPE        "IP Address Error"
     --#SUMMARY     "%s"
     --#ARGUMENTS   { 0 }
     --#SEVERITY    MINOR
     --#TIMEINDEX   1
     --#STATE       OPERATIONAL
     ::= 101

wipUnknownProtocol  TRAP-TYPE
     ENTERPRISE     rmWellfleet
     VARIABLES      { trapDescription }
     DESCRIPTION    "IP Unknown Protocol"
     --#TYPE        "IP Unknown Protocol"
     --#SUMMARY     "%s"
     --#ARGUMENTS   { 0 }
     --#SEVERITY    WARNING
     --#TIMEINDEX   1
     --#STATE       OPERATIONAL
     ::= 102

wipInDiscardError   TRAP-TYPE
     ENTERPRISE     rmWellfleet
     VARIABLES      { trapDescription }
     DESCRIPTION    "IP Input Discard Error"
     --#TYPE        "IP Input Discard Error"
     --#SUMMARY     "%s"
     --#ARGUMENTS   { 0 }
     --#SEVERITY    MINOR
     --#TIMEINDEX   1
     --#STATE       OPERATIONAL
     ::= 103

wipOutDiscardError  TRAP-TYPE
     ENTERPRISE     rmWellfleet
     VARIABLES      { trapDescription }
     DESCRIPTION    "IP Output Discard Error"
     --#TYPE        "IP Output Discard Error"
     --#SUMMARY     "%s"
     --#ARGUMENTS   { 0 }
     --#SEVERITY    MAJOR
     --#TIMEINDEX   1
     --#STATE       OPERATIONAL
     ::= 104

wipNoRoute          TRAP-TYPE
     ENTERPRISE     rmWellfleet
     VARIABLES      { trapDescription }
     DESCRIPTION    "IP No Route To Destination"
     --#TYPE        "IP No Route To Destination"
     --#SUMMARY     "%s"
     --#ARGUMENTS   { 0 }
     --#SEVERITY    MINOR
     --#TIMEINDEX   1
     --#STATE       OPERATIONAL
     ::= 105

wipReassemblyError  TRAP-TYPE
     ENTERPRISE     rmWellfleet
     VARIABLES      { trapDescription }
     DESCRIPTION    "IP Reassembly Error"
     --#TYPE        "IP Reassembly Error"
     --#SUMMARY     "%s"
     --#ARGUMENTS   { 0 }
     --#SEVERITY    MINOR
     --#TIMEINDEX   1
     --#STATE       OPERATIONAL
     ::= 106

wipFragmentError    TRAP-TYPE
     ENTERPRISE     rmWellfleet
     VARIABLES      { trapDescription }
     DESCRIPTION    "IP Fragmentation Error"
     --#TYPE        "IP Fragmentation Error"
     --#SUMMARY     "%s"
     --#ARGUMENTS   { 0 }
     --#SEVERITY    MINOR
     --#TIMEINDEX   1
     --#STATE       OPERATIONAL
     ::= 107


-- ----------------------------------------------------------------------------
--
-- Trap Info
--
-- ----------------------------------------------------------------------------

trapDescription     OBJECT-TYPE
     SYNTAX         DisplayString(1..128)
     ACCESS         not-accessible
     STATUS         mandatory
     DESCRIPTION    "The trap description"
     ::= { srmtrapinfo 1 }

snmpRequestError    TRAP-TYPE
     ENTERPRISE     rmGeneral
     VARIABLES      { trapDescription }
     DESCRIPTION    "SNMP Request Error"
     --#TYPE        "SNMP Request Error"
     --#SUMMARY     "%s"
     --#ARGUMENTS   { 0 }
     --#SEVERITY    CRITICAL
     --#TIMEINDEX   1
     --#STATE       DEGRADED
     ::= 1024

ifUtilThreshold     TRAP-TYPE
     ENTERPRISE     rmGeneral
     VARIABLES      { trapDescription }
     DESCRIPTION    "Interface Utilization exceeds threshold"
     --#TYPE        "Interface utilization"
     --#SUMMARY     "%s"
     --#ARGUMENTS   { 0 }
     --#SEVERITY    INFORMATIONAL
     --#TIMEINDEX   1
     --#STATE       OPERATIONAL
     ::= 1025

srmRouterDiscover   TRAP-TYPE
     ENTERPRISE     rmGeneral
     VARIABLES      { trapDescription }
     DESCRIPTION    "Router was discovered"
     --#TYPE        "Router Discovery"
     --#SUMMARY     "%s"
     --#ARGUMENTS   { 0 }
     --#SEVERITY    INFORMATIONAL
     --#TIMEINDEX   1
     --#STATE       OPERATIONAL
     ::= 1026


-- ----------------------------------------------------------------------------
--
-- Config Uploader Downloader Traps
--
-- ----------------------------------------------------------------------------
srmConfigChanges    TRAP-TYPE
     ENTERPRISE     rmCfgUpDn
     VARIABLES      { trapDescription }
     DESCRIPTION    "Config Uploader/Downloader"
     --#TYPE        "Config Uploader/Downloader"
     --#SUMMARY     "%s"
     --#ARGUMENTS   { 0 }
     --#SEVERITY    INFORMATIONAL
     --#TIMEINDEX   1
     --#STATE       OPERATIONAL
     ::= 1
END
