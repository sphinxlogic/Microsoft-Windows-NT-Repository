-- MIB created 1/17/96 13:41:57, by
--   SMIC (the next generation) version 1.6.29, November 22, 1994.

CISCO-PRODUCTS-MIB DEFINITIONS ::= BEGIN

-- From file: "CISCO-PRODUCTS-MIB.my"

IMPORTS
    ciscoModules, ciscoProducts
            FROM CISCO-SMI;

ciscoProductsMIB OBJECT IDENTIFIER ::= { ciscoModules 2 }
-- MODULE-IDENTITY
--  LastUpdated
--    9505310000Z
--  OrgName
--    Cisco Systems, Inc.
--  ContactInfo
--           Cisco Systems
--     Customer Service
--    
--    Postal: 170 W Tasman Drive
--     San Jose, CA  95134
--     USA
--    
--       Tel: +1 800 553-NETS
--    
--    E-mail: cs-snmp@cisco.com
--  Descr
--    This module defines the object identifiers that are
--    assigned to various hardware platforms, and hence are
--    returned as values for sysObjectID
--  RevDate
--    9505310000Z
--  RevDescr
--    Miscellaneous updates.

ciscoGatewayServer OBJECT IDENTIFIER ::= { ciscoProducts 1 }
ciscoTerminalServer OBJECT IDENTIFIER ::= { ciscoProducts 2 }
ciscoTrouter    OBJECT IDENTIFIER ::= { ciscoProducts 3 }
ciscoProtocolTranslator OBJECT IDENTIFIER ::= { ciscoProducts 4 }
ciscoIGS        OBJECT IDENTIFIER ::= { ciscoProducts 5 }
cisco3000       OBJECT IDENTIFIER ::= { ciscoProducts 6 }
cisco4000       OBJECT IDENTIFIER ::= { ciscoProducts 7 }
cisco7000       OBJECT IDENTIFIER ::= { ciscoProducts 8 }
ciscoCS500      OBJECT IDENTIFIER ::= { ciscoProducts 9 }
cisco2000       OBJECT IDENTIFIER ::= { ciscoProducts 10 }
ciscoAGSplus    OBJECT IDENTIFIER ::= { ciscoProducts 11 }
cisco7010       OBJECT IDENTIFIER ::= { ciscoProducts 12 }
cisco2500       OBJECT IDENTIFIER ::= { ciscoProducts 13 }
cisco4500       OBJECT IDENTIFIER ::= { ciscoProducts 14 }
cisco2102       OBJECT IDENTIFIER ::= { ciscoProducts 15 }
cisco2202       OBJECT IDENTIFIER ::= { ciscoProducts 16 }
cisco2501       OBJECT IDENTIFIER ::= { ciscoProducts 17 }
cisco2502       OBJECT IDENTIFIER ::= { ciscoProducts 18 }
cisco2503       OBJECT IDENTIFIER ::= { ciscoProducts 19 }
cisco2504       OBJECT IDENTIFIER ::= { ciscoProducts 20 }
cisco2505       OBJECT IDENTIFIER ::= { ciscoProducts 21 }
cisco2506       OBJECT IDENTIFIER ::= { ciscoProducts 22 }
cisco2507       OBJECT IDENTIFIER ::= { ciscoProducts 23 }
cisco2508       OBJECT IDENTIFIER ::= { ciscoProducts 24 }
cisco2509       OBJECT IDENTIFIER ::= { ciscoProducts 25 }
cisco2510       OBJECT IDENTIFIER ::= { ciscoProducts 26 }
cisco2511       OBJECT IDENTIFIER ::= { ciscoProducts 27 }
cisco2512       OBJECT IDENTIFIER ::= { ciscoProducts 28 }
cisco2513       OBJECT IDENTIFIER ::= { ciscoProducts 29 }
cisco2514       OBJECT IDENTIFIER ::= { ciscoProducts 30 }
cisco2515       OBJECT IDENTIFIER ::= { ciscoProducts 31 }
cisco3101       OBJECT IDENTIFIER ::= { ciscoProducts 32 }
cisco3102       OBJECT IDENTIFIER ::= { ciscoProducts 33 }
cisco3103       OBJECT IDENTIFIER ::= { ciscoProducts 34 }
cisco3104       OBJECT IDENTIFIER ::= { ciscoProducts 35 }
cisco3202       OBJECT IDENTIFIER ::= { ciscoProducts 36 }
cisco3204       OBJECT IDENTIFIER ::= { ciscoProducts 37 }
ciscoAccessProRC OBJECT IDENTIFIER ::= { ciscoProducts 38 }
ciscoAccessProEC OBJECT IDENTIFIER ::= { ciscoProducts 39 }
cisco1000       OBJECT IDENTIFIER ::= { ciscoProducts 40 }
cisco1003       OBJECT IDENTIFIER ::= { ciscoProducts 41 }
cisco2516       OBJECT IDENTIFIER ::= { ciscoProducts 42 }
cisco1020       OBJECT IDENTIFIER ::= { ciscoProducts 43 }
cisco1004       OBJECT IDENTIFIER ::= { ciscoProducts 44 }
cisco7507       OBJECT IDENTIFIER ::= { ciscoProducts 45 }
cisco7513       OBJECT IDENTIFIER ::= { ciscoProducts 46 }
cisco7506       OBJECT IDENTIFIER ::= { ciscoProducts 47 }
cisco7505       OBJECT IDENTIFIER ::= { ciscoProducts 48 }
cisco1005       OBJECT IDENTIFIER ::= { ciscoProducts 49 }
cisco4700       OBJECT IDENTIFIER ::= { ciscoProducts 50 }
ciscoPro2500PCE OBJECT IDENTIFIER ::= { ciscoProducts 55 }
ciscoPro2501    OBJECT IDENTIFIER ::= { ciscoProducts 56 }
ciscoPro2503    OBJECT IDENTIFIER ::= { ciscoProducts 57 }
ciscoPro2505    OBJECT IDENTIFIER ::= { ciscoProducts 58 }
ciscoPro2507    OBJECT IDENTIFIER ::= { ciscoProducts 59 }
ciscoPro2509    OBJECT IDENTIFIER ::= { ciscoProducts 60 }
ciscoPro2511    OBJECT IDENTIFIER ::= { ciscoProducts 61 }
ciscoPro2514    OBJECT IDENTIFIER ::= { ciscoProducts 62 }
ciscoPro2516    OBJECT IDENTIFIER ::= { ciscoProducts 63 }
cisco2517       OBJECT IDENTIFIER ::= { ciscoProducts 67 }
cisco2518       OBJECT IDENTIFIER ::= { ciscoProducts 68 }
cisco2519       OBJECT IDENTIFIER ::= { ciscoProducts 69 }
cisco2520       OBJECT IDENTIFIER ::= { ciscoProducts 70 }
cisco2521       OBJECT IDENTIFIER ::= { ciscoProducts 71 }
cisco2522       OBJECT IDENTIFIER ::= { ciscoProducts 72 }
cisco2523       OBJECT IDENTIFIER ::= { ciscoProducts 73 }
ciscoPro751     OBJECT IDENTIFIER ::= { ciscoProducts 76 }
ciscoPro752     OBJECT IDENTIFIER ::= { ciscoProducts 77 }
ciscoPro753     OBJECT IDENTIFIER ::= { ciscoProducts 78 }
cisco751        OBJECT IDENTIFIER ::= { ciscoProducts 81 }
cisco752        OBJECT IDENTIFIER ::= { ciscoProducts 82 }
cisco753        OBJECT IDENTIFIER ::= { ciscoProducts 83 }


END
