-- This file contains the concatenation of the following
-- SynOptics MIB modules/files:
--    com3.2-09.30.91
--    enet3.3-10.25.91
--    ieee802.3-1.0-09.30.91
--    tr3.1-10.25.91
--    traps1.0-09.30.91


-- file:  com3.2-09.30.91

SYNOPTICS-COMMON-MIB

-- Common MIB Release 3.2
-- DRAFT Revision 9/30/91
-- Printed 10/7/91

-- Copyright 1991 SynOptics Communications, Inc.  All Rights
-- Reserved.  Reproduction of this document is authorized on
-- condition that the foregoing copyright notice is included.
-- This SynOptics SNMP Management Information Base Specification
-- (Specification) embodies SynOptics' confidential and
-- proprietary intellectual property.  SynOptics retains all
-- title and ownership in the Specification, including any
-- revisions.  
--
-- It is SynOptics intent to encourage the widespread use of
-- this Specification in connection with the management of
-- SynOptics products. SynOptics grants vendors, end-users,
-- and other interested parties a non-exclusive license to
-- use this Specification in connection with the management
-- of SynOptics products.
--
-- This Specification is supplied "AS IS," and SynOptics makes
-- no warranty, either express or implied, as to the use,
-- operation, condition, or performance of the Specification.


DEFINITIONS ::= BEGIN

-- SECTION 1: Top Level Definitions

-- Imports

IMPORTS
	enterprises, Gauge, 
	TimeTicks, IpAddress		FROM RFC1155-SMI
	DisplayString			FROM RFC1213-MIB
	OBJECT-TYPE			FROM RFC-1212;

-- Textual Conventions

S3BackplaneType ::=
	INTEGER {
		other(1),		  -- none of the following
		ethernet(2),		  -- ethernet
		ethernetTokenRing(3),	  -- ethernet and token ring
		ethernetFddi(4),	  -- ethernet and FDDI
		ethernetTokenRingFddi(5), -- ethernet, token ring, and FDDI
		ethernetTokenRingRedundant(6),	-- redundant backplane
		ethernetTokenRingFddiRedund(7)	-- redundant backplane
	}
-- This type is used to specify a concentrator backplane.


S3ChassisType ::=
	INTEGER {
		other(1),	-- none of the following
		m3000(2),	-- model 3000
		m3030(3),	-- model 3030
		m2310(4),	-- model 2310
		m2810(5)	-- model 2810
	}
-- This type is used to specify a concentrator chassis.


S3ModuleType ::=
	INTEGER {
		empty(1),	-- nothing installed
		other(2),	-- none of the following
		m3302(3),	-- STP ethernet Host Module
		m3304-ST(4),	-- FOIRL ethernet Host Module
		m3305(5),	-- UTP ethernet Host Module
		m3308(6),	-- 10 base-T ethernet Host Module
		m3313(7),	-- AUI ethernet NMM w/ RS232 port
		m3313M(8),	-- AUI ethernet NMM w/ RS232 + modem
		m3314-ST(9),	-- FOIRL ethernet NMM w/ RS232
		m3314M-ST(10),	-- FOIRL ethernet NMM w/ RS232 + modem
		m3323(11),	-- AUI Local Bridge
		m3324-ST(12),	-- FOIRL Local Bridge
		m3502(13),	-- STP Token Ring Host Module
		m3532(14),	-- STP Token Ring Repeater
		m3552(15),	-- STP Ring in/ Ring out Module
		m3301(16),	-- Thin Net ethernet Host Module
		m3307(17),	-- 10 base-T 50 pin Host Module
		m3356(18),	-- Ethernet Remote Bridge
		m3512(19),	-- T.R. NMM w/ STP ring in/ring out
		m3514(20),	-- T.R. NMM w/ FOIRL ring in/ring out
		m3505(21),	-- UTP Token Ring Host Module
		m3554(22),	-- FOIRL ring in/ring out Module
		m3534(23),	-- FOIRL Repeater
		m3383(24),	-- AUI ethernet Local Router
		m3384(25),	-- FOIRL ethernet Local Router
		m331x(26),	-- ethernet NMM module w/unknown MDA type
		m351x(27),	-- t.r. NMM module w/unknown MDA type
		m3502-A(28),	-- STP Token Ring Host Module
		m3902(29),	-- STP FDDI Host Module
		m3904(30),	-- Fiber FDDI Host Module
		m3910S(31),	-- FDDI Super NMM
		m3386(32),	-- Cisco Remote Router
		m3394(33),	-- Ethernet-localtalk router
		m3395(34),	-- XYPLEX terminal server
		m3323S(35),	-- High Speed Local Bridge with AUI
		m3324S-ST(36),	-- High Speed Local Bridge with FOIRL
		m3307A(37),	-- 10baseT with amp connector
		m3308A(38),	-- 10baseT (Ibid)
		m3505A(39),	-- UTP Token Ring Host Module
		m3513(40),	-- STP TR repeater NMM
		m3333(41),	-- ethernet retiming module AUI
		m3334-ST(42),	-- ethernet retiming module FOIRL
		m3040(43),	-- model 3040 NCE (SPARCStation on a card)
		m3100R(44),	-- 3100R Summing Module
		m2810-hm(47),	-- host part of 2810 non-modular Ethernet
		m2810-nmm(48)	-- nmm part of 2810 non-modular Ethernet
	}
-- This type is used to specify a module.


S3PsType ::=
	INTEGER {
		other(1),		-- none of the following
		low(2),			-- 200 watt supply (3000)
					-- 50 watt supply (2810)
		medium(3),		-- 360 watt supply (3000)
					-- 110 watt supply (3030)
		high(4),		-- 460 watt supply (3000)
					-- 150 watt supply (3030)
		redundantCapable(5) 	-- redundant backplane (3000)
	}
-- This type is used to specify the power supply type. Where used, the 
-- descriptions specify the valid values.


-- Categories

synoptics			OBJECT IDENTIFIER ::=	{ enterprises 45 }

products			OBJECT IDENTIFIER ::=	{ synoptics 1 }
temporary			OBJECT IDENTIFIER ::=	{ synoptics 2 }
registration			OBJECT IDENTIFIER ::=	{ synoptics 3 }

-- Groups

series1000			OBJECT IDENTIFIER ::=	{ products 1 }
s3SnmpAgent			OBJECT IDENTIFIER ::=	{ products 2 }
series3000			OBJECT IDENTIFIER ::=	{ products 3 }

ieee8023			OBJECT IDENTIFIER ::=	{ temporary 1 }

s3000Chassis			OBJECT IDENTIFIER ::=	{ series3000 1 }
s3000Ethernet			OBJECT IDENTIFIER ::=	{ series3000 2 }
s3000TokenRing			OBJECT IDENTIFIER ::=	{ series3000 3 }
s3000FDDI			OBJECT IDENTIFIER ::=	{ series3000 4 }

s3000Bridge			OBJECT IDENTIFIER ::=	{ series3000 5 }
s3000TerminalServer		OBJECT IDENTIFIER ::=	{ series3000 6 }

s3AgentSw			OBJECT IDENTIFIER ::=	{ s3SnmpAgent 1 }
s3AgentNetProtocol		OBJECT IDENTIFIER ::=	{ s3SnmpAgent 2 }
-- this one is defined in section 4.
-- s3AgentTrapReceiverTable	OBJECT IDENTIFIER ::=	{ s3SnmpAgent 3 }
s3AgentHw			OBJECT IDENTIFIER ::=	{ s3SnmpAgent 4 }
s3AgentSpecific			OBJECT IDENTIFIER ::=	{ s3SnmpAgent 5 }
s3AgentLocImage			OBJECT IDENTIFIER ::=	{ s3SnmpAgent 6 }

s3AgentIpProtocol	OBJECT IDENTIFIER ::=	{ s3AgentNetProtocol 1 }


-- Products
-- These object identifiers are for use as values for sysObjectId.


s3reg-other			OBJECT IDENTIFIER ::=	{ registration 1 }

s3reg-3000			OBJECT IDENTIFIER ::=	{ registration 2 }
s3reg-3000-enetNMM		OBJECT IDENTIFIER ::=	{ s3reg-3000 1 }
s3reg-3000-trNMM		OBJECT IDENTIFIER ::=	{ s3reg-3000 2 }
s3reg-3000-FDDI-NMM		OBJECT IDENTIFIER ::=	{ s3reg-3000 3 }

s3reg-3030			OBJECT IDENTIFIER ::=	{ registration 3 }
s3reg-3030-enetNMM		OBJECT IDENTIFIER ::=	{ s3reg-3030 1 }
s3reg-3030-trNMM		OBJECT IDENTIFIER ::=	{ s3reg-3030 2 }
s3reg-3030-FDDI-NMM		OBJECT IDENTIFIER ::=	{ s3reg-3030 3 }

s3reg-2310			OBJECT IDENTIFIER ::=	{ registration 4 }
s3reg-2310-enetNMM		OBJECT IDENTIFIER ::=	{ s3reg-2310 1 }

s3reg-332X			OBJECT IDENTIFIER ::=	{ registration 5 }
s3reg-332XS			OBJECT IDENTIFIER ::=	{ registration 6 }
s3reg-3356			OBJECT IDENTIFIER ::=	{ registration 7 }

s3reg-2810			OBJECT IDENTIFIER ::=	{ registration 8 }
s3reg-2810-enetNMM		OBJECT IDENTIFIER ::=	{ s3reg-2810 1 }


-- SECTION 2: Concentrator Chassis
-- Chassis Group

-- Implementation of this group is mandatory for all SynOptics Series 3000 
-- agents.

s3ChassisType OBJECT-TYPE
	SYNTAX	S3ChassisType
	ACCESS	read-only
	STATUS	mandatory
	DESCRIPTION
		"The chassis type."
	::= { s3000Chassis 1 }

s3ChassisBkplType OBJECT-TYPE
	SYNTAX	S3BackplaneType
	ACCESS	read-only
	STATUS	mandatory
	DESCRIPTION
		"The chassis backplane type."
   		::= { s3000Chassis 2 }

s3ChassisBkplRev OBJECT-TYPE
	SYNTAX	INTEGER
	ACCESS	read-only
	STATUS	mandatory
	DESCRIPTION
		"The chassis backplane revision."
	::= { s3000Chassis 3 }

s3ChassisPsType OBJECT-TYPE
	SYNTAX	S3PsType
	ACCESS	read-only
	STATUS	mandatory
	DESCRIPTION
		"The chassis power supply type."
	::= { s3000Chassis 4 }

s3ChassisPsStatus OBJECT-TYPE
	SYNTAX	INTEGER {
		ok(1),			-- supply ok
		primaryFail(2),		-- primary power supply failure
		secondaryFail(3),	-- secondary power supply failure
		bothFail(4)		-- both power supplies failed
	}
	ACCESS	read-only
	STATUS	mandatory
	DESCRIPTION
		"The chassis power supply status."
	::= { s3000Chassis 5 }

s3ChassisFanStatus OBJECT-TYPE
	SYNTAX	INTEGER {
		ok(1),			-- fans are running
		fail(2),		-- fan(s) are broken
		other(3)		-- unknown fan status or no fan
	}
	ACCESS	read-only
	STATUS	mandatory
	DESCRIPTION
		"The status of the chassis cooling fan."
	::= { s3000Chassis 6 }



-- Chassis Slot Configuration Table


s3SlotConfigTable OBJECT-TYPE
	SYNTAX	SEQUENCE OF S3SlotConfigEntry
	ACCESS	not-accessible
	STATUS	mandatory
	DESCRIPTION
		"The chassis slot configuration table."
	::= { s3000Chassis 7 }

s3SlotConfigEntry OBJECT-TYPE
	SYNTAX	S3SlotConfigEntry
	ACCESS	not-accessible
	STATUS	mandatory
	DESCRIPTION
		"What type of module is in each slot of the chassis."
	INDEX	{ s3SlotNumber }
	::= { s3SlotConfigTable 1 }


S3SlotConfigEntry ::= SEQUENCE {
	s3SlotNumber
		INTEGER,
	s3SlotModuleId
		INTEGER,
	s3SlotModuleType
		S3ModuleType,
	s3SlotModuleDescr
		DisplayString,
	s3SlotModuleLed
		OCTET STRING,
	s3SlotModuleMdaId
		INTEGER
}

s3SlotNumber OBJECT-TYPE
	SYNTAX	INTEGER
	ACCESS	read-only
	STATUS	mandatory
	DESCRIPTION
		"The 3000 Chassis slot number. Valid entries are 1-12."
	::= { s3SlotConfigEntry 1 }

s3SlotModuleId OBJECT-TYPE
	SYNTAX	INTEGER
	ACCESS	read-only
	STATUS	mandatory
	DESCRIPTION
		"ID for the module."
	::= { s3SlotConfigEntry 2 }

s3SlotModuleType OBJECT-TYPE
	SYNTAX	S3ModuleType
	ACCESS	read-only
	STATUS	deprecated
	DESCRIPTION
		"The type of module this entry represents."
	::= { s3SlotConfigEntry 3 }

s3SlotModuleDescr OBJECT-TYPE
	SYNTAX	DisplayString (SIZE(0..128))
	ACCESS	read-only
	STATUS	mandatory
	DESCRIPTION
		"Module description."
	::= { s3SlotConfigEntry 4 }

s3SlotModuleLed OBJECT-TYPE
	SYNTAX	OCTET STRING (SIZE(8))
	ACCESS	read-only
	STATUS	mandatory
	DESCRIPTION
		"Status of the module LEDs."
	::= { s3SlotConfigEntry 5 }

s3SlotModuleMdaId OBJECT-TYPE
	SYNTAX	INTEGER
	ACCESS	read-only
	STATUS	mandatory
	DESCRIPTION
		"ID of the medium-dependent part of the board.  The value
		is board dependent."
	::= { s3SlotConfigEntry 6 }



-- Chassis Common Board Table


s3CommonBoardTable OBJECT-TYPE
	SYNTAX	SEQUENCE OF S3CommonBoardEntry
	ACCESS	not-accessible
	STATUS	mandatory
	DESCRIPTION
		"A table containing information about the boards currently 
		plugged	into the 3000 Chassis.  This board table contains an 
		entry for each non-empty slot in the s3SlotConfigTable, EXCEPT
		for those slots containing Retiming Modules.
		All of the information in this board table is retrievable 
		using the NMI commands that are common to all boards integrated
 		into the SynOptics Series 3000 Concentrators."
	::= { s3000Chassis 8 }

s3CommonBoardEntry OBJECT-TYPE
	SYNTAX	S3CommonBoardEntry
	ACCESS	not-accessible
	STATUS	mandatory
	DESCRIPTION
		"A table entry containing information about a single Board 
		currently plugged into the 3000 Chassis. These values can be 
		retrieved using the common board NMI commands."
	INDEX	{ s3CommonBoardIndex }
	::= { s3CommonBoardTable 1 }

S3CommonBoardEntry ::= SEQUENCE {
	s3CommonBoardIndex
		INTEGER,
	s3CommonBoardId
		INTEGER,
	s3CommonBoardHwVer
		INTEGER,
	s3CommonBoardStatus
		INTEGER,
	s3CommonBoardReset
		INTEGER,
	s3CommonBoardPartStatus
		INTEGER,
	s3CommonBoardNmCntlStatus
		INTEGER,
	s3CommonBoardPsStatus
		INTEGER
}

s3CommonBoardIndex OBJECT-TYPE
	SYNTAX	INTEGER
	ACCESS	read-only
	STATUS	mandatory
	DESCRIPTION
		"A unique value for each board. Its value ranges between 1 and
		12. The value for each board must remain constant at least from
		one re-initialization of the entity's network management system
		to the next re-initialization."
	::= { s3CommonBoardEntry 1 }

s3CommonBoardId OBJECT-TYPE
	SYNTAX	INTEGER
	ACCESS	read-only
	STATUS	mandatory
	DESCRIPTION
		"ID of the board."
	::= { s3CommonBoardEntry 2 }

s3CommonBoardHwVer OBJECT-TYPE
	SYNTAX	INTEGER
	ACCESS	read-only
	STATUS	mandatory
	DESCRIPTION
		"The hardware revision of the board.  0=Rev. A, 1=Rev. B, etc."
	::= { s3CommonBoardEntry 3 }

s3CommonBoardStatus OBJECT-TYPE
	SYNTAX	INTEGER {
		ok(1),		-- good status
		fail(2)		-- bad status
		}
	ACCESS	read-only
	STATUS	mandatory
	DESCRIPTION
		"This indicates the operational status of the board."
	::= { s3CommonBoardEntry 4 }

s3CommonBoardReset OBJECT-TYPE
	SYNTAX	INTEGER {
		noReset(1),	-- not resetting
		reset(2)	-- resetting
		}
	ACCESS	read-write
	STATUS	mandatory
	DESCRIPTION
		"This indicates the reset state of the board.  Writing with 
		the value reset (2) will reset the board."
	::= { s3CommonBoardEntry 5 }

s3CommonBoardPartStatus OBJECT-TYPE
	SYNTAX	INTEGER {
		enabled(1),	-- board enabled
		partition(2)	-- board partitioned indefinitely
		}
	ACCESS	read-write
	STATUS	mandatory
	DESCRIPTION
		"Tells whether the board is partitioned or enabled.  Writing 
		with the value partition(2) will partition the board 
		indefinitely and writing with the value enabled(1) will enable
		the board. Boards cannot be partitioned in the 2810 
		concentrator.  The 2810 agent will implement this object as 
		read-only."
	::= { s3CommonBoardEntry 6 }

s3CommonBoardNmCntlStatus OBJECT-TYPE
	SYNTAX	INTEGER {
			notNmControl(1),	-- board not under NM control
			nmControl(2)		-- board under NM control
			}
	ACCESS	read-only
	STATUS	mandatory
	DESCRIPTION
		"Tells whether the board is under network management control.
  		The value nmControl(2) indicates that the board or one or more
 		ports are being controlled by network management.  This means 
		that the board or one or more ports are partitioned via a 
		network manager."
	::= { s3CommonBoardEntry 7 }

s3CommonBoardPsStatus OBJECT-TYPE
	SYNTAX	INTEGER {
			ok(1),		-- good status
			fail(2)		-- bad status
			}
	ACCESS	read-only
	STATUS	mandatory
	DESCRIPTION
		"This indicates the operational status of the board power 
		supply.  A fail(2) indicates that one of the power supplies 
		on the board has failed."
	::= { s3CommonBoardEntry 8 }


-- Packed Slot Configuration Table


s3SlotConfigOctetString OBJECT-TYPE
	SYNTAX	OCTET STRING (SIZE(12..144))
	ACCESS	read-only
	STATUS	mandatory
	DESCRIPTION
		"Packed octet string for the slot configuration table."
	::= { s3000Chassis 9 }



-- SECTION 3: Agent Configuration

-- Agent Software Group


-- Implementation of this group is mandatory for all SynOptics Series 3000 
-- agents


s3AgentType OBJECT-TYPE
	SYNTAX	INTEGER {
		other(1),	-- none of the following
		m3313(2),	-- AUI Ethernet NMM w/ RS232 port
		m3313M(3),	-- AUI Enet NMM w/ RS232 port + modem
		m3314-ST(4),	-- FOIRL Ethernet NMM w/ RS232
		m3314M-ST(5),	-- FOIRL Ethernet NMM w/ RS232 + modem
		m2310(6),	-- Model 2310
		m3512(7),	-- T.R. NMM w/ STP ring in/ring out
		m3514(8),	-- T.R. NMM w/ FOIRL ring in/ring out
		m332X(9),	-- Low Speed Local Bridge
		m3356(10),	-- Ethernet Remote Bridge
		m332XS(11)	-- High Speed Local Bridge
	}
	ACCESS	read-only
	STATUS	mandatory
	DESCRIPTION
		"The 3000 series agent's Module type."
	::= {s3AgentSw  1 }

s3AgentFwVer OBJECT-TYPE
	SYNTAX	INTEGER
	ACCESS	read-only
	STATUS	mandatory
	DESCRIPTION
		"The agent's module firmware version 0=Rev A,1=Rev B,etc."
	::= { s3AgentSw 2 }

s3AgentSwMajorVer OBJECT-TYPE
	SYNTAX	INTEGER
	ACCESS	read-only
	STATUS	mandatory
	DESCRIPTION
		"The network management module major software version number 
		(i.e. represents major.minor or 3.0).  Object is in decimal."
	::= { s3AgentSw 3 }

s3AgentSwMinorVer OBJECT-TYPE
	SYNTAX	INTEGER
	ACCESS	read-only
	STATUS	mandatory
	DESCRIPTION
		"The network management module minor software version number 
		(i.e. represents major.minor or 3.0).  Object is in decimal."
	::= { s3AgentSw 4 }

s3AgentBootProtocol OBJECT-TYPE
	SYNTAX	INTEGER {
		other(1),	-- boot protocol not listed here
		bootp-tftp(2),
		tftp-only(3),
		ieee802-1e(4),
		proprietary(5),	-- supported proprietary boot protocol
		dll-download(6)	-- direct async binary download (Retix)
	}
	ACCESS	read-only
	STATUS	mandatory
	DESCRIPTION
		"Boot protocol used to load the module with its software."
	::= {s3AgentSw 5 }

s3AgentBootFile OBJECT-TYPE
	SYNTAX	DisplayString (SIZE(0..64))
	ACCESS	read-write
	STATUS	mandatory
	DESCRIPTION
		"The name of the boot file that is sent to the file server 
		during boot time. The actual boot protocol used to retrieve the
		file is determined by s3AgentBootProtocol. This parameter will
 		not take effect until written into EEPROM (s3AgentWriteEeprom)
 		and a reset (s3AgentReset) is issued. This parameter is used 
		only if the s3AgentBootMode is set to use EEPROM."
	::= { s3AgentSw 6 }

s3AgentAuthTrap OBJECT-TYPE
	SYNTAX	INTEGER {
		disable(1),	-- disable authentication traps
		enable(2)	-- enable authentication traps
	}
	ACCESS	read-write
	STATUS	mandatory
	DESCRIPTION
		"Enable or disable the use of authentication error trap 
		generation. This parameter will take effect only after a 
		restart (s3AgentRestart) is issued.  This parameter will not 
		survive a reset (s3AgentReset) unless the specific NMM 
		configuration file is updated to reflect the change."
	::= { s3AgentSw 7 }

s3AgentLocation OBJECT-TYPE
	SYNTAX	DisplayString (SIZE(0..64))
	ACCESS	read-write
	STATUS	mandatory
	DESCRIPTION
		"This is a informational string that could be used to show the
		physical location (i.e. area) of the NMM or concentrator. This
 		parameter will take effect only after a restart 
		(s3AgentRestart) is issued.  This parameter will not survive a
 		reset (s3AgentReset) unless the specific NMM configuration file
 		is updated to reflect the change."
	::= { s3AgentSw 8 }

s3AgentMibLevel OBJECT-TYPE
	SYNTAX	INTEGER
	ACCESS	read-only
	STATUS	mandatory
	DESCRIPTION
		"Used to determine current MIB release supported by agent.  The
		encoding of this object is of the following form: xyy, where x
		is the major version number and yy is the minor version number.
  	        Thus, version 3.0 would be represented as 300,  version 3.01 
		would be 301 and 3.1 would be 310.  Object is in decimal."
	::= { s3AgentSw 9 }

s3AgentFeatureLevel OBJECT-TYPE
	SYNTAX	INTEGER
	ACCESS	read-only
	STATUS	mandatory
	DESCRIPTION
		"Used to determine feature level of the agent.  The encoding 
		of this object is of the following form: xyy, where x is the 
		major version number and yy is the minor version number.  Thus,
  	        feature level version 1.0 would be represented as 100, version
 		1.01 would be 101 and 1.1 would be 110. Object is in decimal."
	::= { s3AgentSw 10 }


s3AgentMySlotId OBJECT-TYPE
	SYNTAX	INTEGER
	ACCESS	read-only
	STATUS	mandatory
	DESCRIPTION
		"Slot where this agent currently resides.  If hardware is 
		unable to determine then a 0 should be returned."
	::= { s3AgentSw 11 }


-- Agent Network Protocol Group


-- Implementation of this group is mandatory for all SynOptics Series 3000 
-- agents.


s3AgentIpAddr OBJECT-TYPE
	SYNTAX	IpAddress
	ACCESS	read-write
	STATUS	mandatory
	DESCRIPTION
		"The network management module's administrative IP address.  
		The current operational IP address can be obtained by the 
		ipAdEntAddr entry in the ipAddrTable. This parameter will take
 		effect only after a restart (s3AgentRestart) is issued.  This 
		parameter will not survive a reset (s3AgentReset) unless it is
 		written into EEPROM (s3AgentWriteEeprom).  This parameter is 
		used only if the s3AgentBootMode is set to use EEPROM."
	::= { s3AgentIpProtocol 1 }

s3AgentNetMask OBJECT-TYPE
	SYNTAX	IpAddress
	ACCESS	read-write
	STATUS	mandatory
	DESCRIPTION
		"The network management module's administrative subnet mask.  
		The current operational subnet mask can be obtained by the 
		ipAdEntNetMask entry in the ipAddrTable. This parameter will `
		take effect only after a restart (s3AgentRestart) is issued. 
		This parameter will not survive a reset (s3AgentReset) unless 
		it is written into EEPROM (s3AgentWriteEeprom).  This parameter
		is used only if the agentBootMode is set to use EEPROM.
		NOTE:  The Model 331x (3313, 3313M, 3314-ST, 3314M-ST)
		Ethernet NMM agents do not store this parameter in EEPROM, 
		so for these agents the subnet mask configuration must be
		downloaded in the configuration file."
	::= { s3AgentIpProtocol 2 }

s3AgentDefaultGateway OBJECT-TYPE
	SYNTAX	IpAddress
	ACCESS	read-write
	STATUS	mandatory
	DESCRIPTION
		"The network management module's administrative default 
		gateway IP address.  The current operational default gateway's
 		IP address can be obtained from the ipRoutingTable. This 
		parameter will take effect only after a restart 
		(s3AgentRestart) is issued.  This parameter will not survive a
 		reset (s3AgentReset) unless it is written into EEPROM 
		(s3AgentWriteEeprom).  This parameter is used only if the 
		agentBootMode is set to use EEPROM."
	::= { s3AgentIpProtocol 3 }

s3AgentBootServerAddr OBJECT-TYPE
	SYNTAX	IpAddress
	ACCESS	read-write
	STATUS	mandatory
	DESCRIPTION
		"The IP address to which the requests for boot files are sent.
 		The protocol used to retrieve the boot files is determined by 
		object s3AgentBootProtocol. This parameter will not take effect
 		until until written into EEPROM (s3AgentWriteEeprom) and a 
		reset (s3AgentReset) is issued. This parameter is used only if
 		the s3AgentBootMode is set to use EEPROM."
	::= { s3AgentIpProtocol 4 }



-- Agent Trap Receiver Table


-- Implementation of this group is mandatory for all SynOptics Series 3000 agents


s3AgentTrapReceiverTable OBJECT-TYPE
	SYNTAX	SEQUENCE OF S3AgentTrapReceiverEntry
	ACCESS	not-accessible
	STATUS	mandatory
	DESCRIPTION
		"Table containing list of NMS's that are to receive traps 
		generated by this NMM."
	::= { s3SnmpAgent 3 }

s3AgentTrapReceiverEntry OBJECT-TYPE
	SYNTAX	S3AgentTrapReceiverEntry
	ACCESS	not-accessible
	STATUS	mandatory
	DESCRIPTION
		"A destination address and community string to a particular 
		trap server, along with a trap filter and entry aging 
		capability."
	INDEX	{ s3AgentTrapRcvrNetAddress }
	::= { s3AgentTrapReceiverTable 1 }

S3AgentTrapReceiverEntry ::= SEQUENCE {
	s3AgentTrapRcvrStatus
		INTEGER,
	s3AgentTrapRcvrNetAddress
		OCTET STRING,
	s3AgentTrapRcvrComm
		OCTET STRING,
	s3AgentTrapRcvrAgeTime
		TimeTicks
}

s3AgentTrapRcvrStatus OBJECT-TYPE
	SYNTAX	INTEGER {
		other (1),		-- none of the following
		valid (2),		-- a valid address
		invalid (3)		-- an invalid address
	}
	ACCESS	read-write
	STATUS	mandatory
	DESCRIPTION
		"Setting this object to the value invalid(3) has the effect 
		of invalidating the corresponding entry in the 
		s3AgentTrapReceiverTable. That is, it effectively disassociates
 		the address identified with the entry by removing the entry 
		from the table. On a read the value of valid(2) should be 
		returned if the entry contains a valid record, or invalid(3) 
		should be returned if the entry contains an invalid record."
	::= { s3AgentTrapReceiverEntry 1 }

s3AgentTrapRcvrNetAddress OBJECT-TYPE
	SYNTAX	OCTET STRING (SIZE(4))
	ACCESS	read-write
	STATUS	mandatory
	DESCRIPTION
		"IP address for trap server that is to receive the trap."
	::= { s3AgentTrapReceiverEntry  2 }

s3AgentTrapRcvrComm OBJECT-TYPE
	SYNTAX	OCTET STRING (SIZE(0..20))
	ACCESS	read-write
	STATUS	mandatory
	DESCRIPTION
		"Community string used for traps sent to this trap receiver."
	::= { s3AgentTrapReceiverEntry  3 }

s3AgentTrapRcvrAgeTime OBJECT-TYPE
	SYNTAX	TimeTicks
	ACCESS	read-write
	STATUS	mandatory
	DESCRIPTION
		"This is the time interval used to age entries out of the trap
 		receiver table.  The default value if not specified will be 0,
 		or infinite, never to be aged out."
	::= { s3AgentTrapReceiverEntry  4 }



-- Agent Hardware Group


-- Implementation of this group is mandatory for all SynOptics Series 3000 
-- agents.


				
s3AgentStatus OBJECT-TYPE
	SYNTAX	INTEGER {
		offline(1),	-- the agent is offline
		online(2)	-- the agent is online
	}
	ACCESS	read-only
	STATUS	mandatory
	DESCRIPTION
		"This indicates whether the NMM is online(2) and operating, or 
		offline(1) (ie: not connected to the concentrator backplane)."
	::= { s3AgentHw 1 }

s3AgentMdaHwVer OBJECT-TYPE
	SYNTAX	INTEGER
	ACCESS	read-only
	STATUS	mandatory
	DESCRIPTION
		"The network management module's MDA hardware version number 
		(0=Rev. A, 1=Rev. B, etc.)."
	::= { s3AgentHw 2 }

s3AgentMode OBJECT-TYPE
	SYNTAX	INTEGER {
		primary(1),	-- in primary mode
		secondary(2),	-- in secondary mode
		other(3)	-- the other values do not apply
	}
	ACCESS	read-write
	STATUS	mandatory
	DESCRIPTION
		"This indicates whether the NMM is operating in primary(1) or 
		secondary(2) mode."
	::= { s3AgentHw 3 }

s3AgentReset OBJECT-TYPE
	SYNTAX	INTEGER {
		noReset(1),	-- not resetting
		reset(2)	-- reset
	}
	ACCESS	read-write
	STATUS	mandatory
	DESCRIPTION
		"Network management module reset status.  Writing a reset(2) 
		to this object will reset the NMM (stop refreshing the watch 
		dog) and perform a download and restart.  This process takes 
		about 45 seconds."
	::= { s3AgentHw 4 }

s3AgentRestart OBJECT-TYPE
	SYNTAX	INTEGER {
		noRestart(1),	-- not restarting
		restart(2)	-- restart
	}
	ACCESS	read-write
	STATUS	mandatory
	DESCRIPTION
		"Network management module restart status.  Writing a 
		restart(2) to this object will restart the NMM.  This 
		initializes all the counters, re-reads the EEPROM data 
		structure and starts executing from the beginning of the code."
	::= { s3AgentHw 5 }

s3AgentBootMode OBJECT-TYPE
	SYNTAX	INTEGER {
		eeprom(1),	-- get boot info from eeprom
		other(2)	-- or from a boot protocol
	}
	ACCESS	read-write
	STATUS	mandatory
	DESCRIPTION
		"The method for obtaining boot parameter information.
		This parameter will not take effect until written into EEPROM 
		(s3AgentWriteEeprom) and a reset (s3AgentReset) is issued."
	::= { s3AgentHw 6 }

s3AgentWriteEeprom OBJECT-TYPE
	SYNTAX	INTEGER {
		noWriteEeprom(1),	-- not writing EEPROM 
		writeEeprom(2)		-- write EEPROM
	}
	ACCESS	read-write
	STATUS	mandatory
	DESCRIPTION
		"Network management module EEPROM write status.  Writing a 
		(2) to this object will write the contents of current EEPROM 
		data structure in the EEPROM."
	::= { s3AgentHw 7 }

s3AgentBaudRate OBJECT-TYPE
	SYNTAX	Gauge
	ACCESS	read-write
	STATUS	mandatory
	DESCRIPTION
		"Specifies the baud rate in bits per second of either the 
		internal modem or the RS-232 port. This parameter will take 
		effect only after a restart (s3AgentRestart) is issued.  This 
		parameter will not survive a reset (s3AgentReset) unless the 
		specific NMM configuration file is updated to reflect the 
		change."
	::= { s3AgentHw 8 }

s3AgentInitString OBJECT-TYPE
	SYNTAX	OCTET STRING (SIZE(0..64))
	ACCESS	read-write
	STATUS	mandatory
	DESCRIPTION
		"This is the initialization string used to establish the 
		out-of-band connection. (i.e. could contain the string 
		ATDT,415-960-1100 for an internal or external modem). This 
		parameter will take effect only after a restart 
		(s3AgentRestart) is issued.  This parameter will not survive 
		a reset (s3AgentReset) unless the specific NMM configuration
 		file is updated to reflect the change."
	::= { s3AgentHw 9 }


-- Agent Local Image Group


-- This group is mandatory for agents with image code stored in local EPROM.
-- Other agents should return NoSuch if asked for any of the objects in this group.


s3LocImageValid OBJECT-TYPE
	SYNTAX	INTEGER {
		other(1),		-- unknown status
		localImageValid(2),	-- local image is valid
		localImageInvalid(3)	-- local image is invalid
	}
	ACCESS	read-only
	STATUS	mandatory
	DESCRIPTION
		"This indicates whether the agent has a valid local code 
		image on board. An EPROM checksum failure would cause the 
		agent to return localImageInvalid(3)."
	::= { s3AgentLocImage 1 }

s3LocImageMajorVersion OBJECT-TYPE
	SYNTAX	INTEGER
	ACCESS	read-only
	STATUS	mandatory
	DESCRIPTION
		"The major software version number of the locally-stored image.
  		 This object applies only to agents with valid local image.  
		 Other agents should return zero."
	::= { s3AgentLocImage 2 }

s3LocImageMinorVersion OBJECT-TYPE
	SYNTAX	INTEGER
	ACCESS	read-only
	STATUS	mandatory
	DESCRIPTION
		"The minor software version number of the locally-stored image.
  		This object applies only to agents with valid local image.  
		Other agents should return zero."
	::= { s3AgentLocImage 3 }

s3LocImageLoadMode OBJECT-TYPE
	SYNTAX	INTEGER {
		other(1),		-- unknown status
		remoteBoot(2),		-- use net, not local image
		localBoot(3),		-- boot from local image, not net
		localAsBackup(4)	-- try net, if fails use local
	}
	ACCESS	read-write
	STATUS	mandatory
	DESCRIPTION
		"This indicates whether the agent should get code from the 
		network, use a local image, or try the network first and then 
		fall back to local image if the network boot fails.  The 
		localBoot and localAsBackup values apply only to agents with 
		local load option."
	::= { s3AgentLocImage 4 }

s3LocImageActualSource OBJECT-TYPE
	SYNTAX	INTEGER {
		other(1),		-- unknown status
		remoteImage(2),		-- downloaded code from network
		localImage(3)		-- loaded code from local EPROM
	}
	ACCESS	read-only
	STATUS	mandatory
	DESCRIPTION
		"This indicates whether the agent loaded code from the network
 		or used a local image.  When the the ImageLoadMode is 
		localAsBackup, this variable indicates whether the network 
		load was successful."
	::= { s3AgentLocImage 5 }


END


-- file:  enet3.3-10.25.91

SYNOPTICS-ETHERNET-MIB

-- Ethernet MIB Release 3.3
-- DRAFT Revision 10/25/91
-- Printed 10/25/91

-- Copyright 1991 SynOptics Communications, Inc.  All Rights
-- Reserved.  Reproduction of this document is authorized on
-- condition that the foregoing copyright notice is included.
-- This SynOptics SNMP Management Information Base Specification
-- (Specification) embodies SynOptics' confidential and
-- proprietary intellectual property.  SynOptics retains all
-- title and ownership in the Specification, including any
-- revisions.  
--
-- It is SynOptics intent to encourage the widespread use of
-- this Specification in connection with the management of
-- SynOptics products. SynOptics grants vendors, end-users,
-- and other interested parties a non-exclusive license to
-- use this Specification in connection with the management
-- of SynOptics products.
--
-- This Specification is supplied "AS IS," and SynOptics makes
-- no warranty, either express or implied, as to the use,
-- operation, condition, or performance of the Specification.


DEFINITIONS ::= BEGIN

-- SECTION 1: Top Level Definitions

-- Imports

IMPORTS
	Counter, IpAddress, Gauge	FROM RFC1155-SMI
	DisplayString			FROM RFC1213-MIB
	OBJECT-TYPE			FROM RFC-1212
	s3000Ethernet			FROM SYNOPTICS-COMMON-MIB;


-- Groups

s3000EnetConcentrator	OBJECT IDENTIFIER ::= { s3000Ethernet 1 }
s3000EnetBoard		OBJECT IDENTIFIER ::= { s3000Ethernet 2 }
s3000EnetLocBridge	OBJECT IDENTIFIER ::= { s3000EnetBoard 2 }
s3000EnetRemBridge	OBJECT IDENTIFIER ::= { s3000EnetBoard 3 }
s3000EnetRouter		OBJECT IDENTIFIER ::= { s3000EnetBoard 4 }
s3000EnetPort 		OBJECT IDENTIFIER ::= { s3000Ethernet 3 }
s3000EnetNmm		OBJECT IDENTIFIER ::= { s3000Ethernet 4 }



-- SECTION 2: Ethernet Status and Statistics Group

-- The Ethernet Status and Statistics group consists of Concentrator Group,
-- Board Table, Local Bridge Board Table, Local Bridge Port Table,
-- Remote Bridge Board Table, Remote Bridge Port Table, Router Board
-- Table, and Port Table.


-- Concentrator Group

-- Implementation of this group is mandatory for all 
-- SynOptics Series 3000 Ethernet NMM agents

s3EnetConcRetimingStatus OBJECT-TYPE
	SYNTAX	INTEGER {
		off(1),		-- retiming off
		on(2)		-- retiming on
	}
	ACCESS	read-write
	STATUS	mandatory
	DESCRIPTION
		"Does this concentrator have retiming turned on.  Writing a 1 
		will turn off retiming and writing a 2 will turn on retiming. 
 		This will change the active state of retiming but will change 
		the value in EEPROM only when agentWriteEeprom is set.The 
		factory default of this state is on. Retiming cannot be 
		disabled in the 2810 concentrator.  The 2810 agent will
		implement this object as read-only."
	::= { s3000EnetConcentrator 1 }

s3EnetConcFrmsRxOk OBJECT-TYPE
	SYNTAX	Counter
	ACCESS	read-only
	STATUS	mandatory
	DESCRIPTION
		"This contains a count of frames that are successfully 
		received by the concentrator. This does not include frames 
		received with a frame-too-long, runt, FCS, or alignment errors.
		This counter includes broadcast and multicast frames that are 
		received."
	::= { s3000EnetConcentrator 2 }

s3EnetConcOctetsRxOk OBJECT-TYPE
	SYNTAX	Counter
	ACCESS	read-only
	STATUS	mandatory
	DESCRIPTION
		"Contains a count of data and padding octets in frames that 
		are successfully received by the concentrator.  This does not 
		include frames received with a frame-too-long, runt, FCS, or 
		alignment errors. This counter includes octets in broadcast 
		and multicast frames that are received. This counter does not 
		include the octets in the address, length/type and CRC fields."
	::= { s3000EnetConcentrator 3 }

s3EnetConcMcastFrmsRxOk OBJECT-TYPE
	SYNTAX	Counter
	ACCESS	read-only
	STATUS	mandatory
	DESCRIPTION
		"This contains a count of frames that are successfully 
		received by the concentrator and are directed to an active 
		non-broadcast group address. This does not include frames 
		received with a frame-too-long, runt, FCS, or alignment errors.
		Only frames that are for a multicast address that this 
		interface is receiving are counted.  Broadcast packets are 
		not included."
	::= { s3000EnetConcentrator 4 }

s3EnetConcBcastFrmsRxOk OBJECT-TYPE
	SYNTAX	Counter
	ACCESS	read-only
	STATUS	mandatory
	DESCRIPTION
		"This contains a count of frames that are successfully received
		by the concentrator and are directed to the broadcast group 
		address. This does not include frames received with a 
		frame-too-long, runt, FCS, or alignment errors. Multicast 
		packets are not included."
	::= { s3000EnetConcentrator 5 }

s3EnetConcColls OBJECT-TYPE
	SYNTAX	Counter
	ACCESS	read-only
	STATUS	mandatory
	DESCRIPTION
		"This contains a count of the collision flags at the 
		concentrator level."
	::= { s3000EnetConcentrator 6 }


-- MAC Receive Error Statistics

-- A hierarchical order has been established for those objects listed below 
-- such that when multiple error conditions can be associated with one frame, 
-- only one condition is counted.  This hierarchy, in descending order is:
--	frame too long
--	runt frames
--	fragments
--	alignment error
--	frame check error


s3EnetConcTooLongErrors OBJECT-TYPE
	SYNTAX	Counter
	ACCESS	read-only
	STATUS	mandatory
	DESCRIPTION
		"This contains a count of frames that are received by the 
		concentrator and exceed the maximum permitted frame size.  
		This counter is incremented when the frameTooLong error is 
		detected."
	::= { s3000EnetConcentrator 7 }

s3EnetConcRuntErrors OBJECT-TYPE
	SYNTAX	Counter
	ACCESS	read-only
	STATUS	mandatory
	DESCRIPTION
		"This contains a count of frames received by the concentrator 
		that are less than the minimum permitted frame size and have a
 		good FCS."
	::= { s3000EnetConcentrator 8 }

s3EnetConcFragErrors OBJECT-TYPE
	SYNTAX	Counter
	ACCESS	read-only
	STATUS	mandatory
	DESCRIPTION
		"This contains a count of frames received by the concentrator 
		that are less than the minimum permitted frame size and have a
 		bad FCS or alignment error."
	::= { s3000EnetConcentrator 9 }

s3EnetConcAlignErrors OBJECT-TYPE
	SYNTAX	Counter
	ACCESS	read-only
	STATUS	mandatory
	DESCRIPTION
		"This contains a count of frames received by the concentrator 
		that are not an integral number of octets in length and do not
 		pass the FCS check.  This counter is incremented when the 
		alignment Error status is detected."
	::= { s3000EnetConcentrator 10 }

s3EnetConcFcsErrors OBJECT-TYPE
	SYNTAX	Counter
	ACCESS	read-only
	STATUS	mandatory
	DESCRIPTION
		"This contains a count of frames received by the concentrator 
		that are an integral number of octets in length that do not 
		pass the FCS check.  This counter is incremented when the 
		frame Check Error status is detected."
	::= { s3000EnetConcentrator 11 }

s3EnetConcLateCollErrors OBJECT-TYPE
	SYNTAX	Counter
	ACCESS	read-only
	STATUS	mandatory
	DESCRIPTION
		"This contains a total concentrator count of the late 
		collision flags."
	::= { s3000EnetConcentrator 12 }


-- Board Table


s3EnetBoardTable OBJECT-TYPE
	SYNTAX	SEQUENCE OF S3EnetBoardEntry
	ACCESS	not-accessible
	STATUS	mandatory
	DESCRIPTION
		"A table of board-related objects.  The number of entries is 
		given by the number of Ethernet host module and network 
		management module boards that are contained in the 
		Concentrator Slot Configuration Table."
	::= { s3000EnetBoard 1 }

s3EnetBoardEntry OBJECT-TYPE
	SYNTAX	S3EnetBoardEntry
	ACCESS	not-accessible
	STATUS	mandatory
	DESCRIPTION
		"A table containing objects about Ethernet boards which are 
		currently plugged into the 3000 chassis."
	INDEX	{ s3EnetBoardIndex }
	::= { s3EnetBoardTable 1 }

S3EnetBoardEntry ::= SEQUENCE {
	s3EnetBoardIndex
		INTEGER,
-- the bounded below objects are deprecated
	s3EnetBoardType
		INTEGER,
	s3EnetBoardHwVer
		INTEGER,
	s3EnetBoardStatus
		INTEGER,
	s3EnetBoardReset
		INTEGER,
	s3EnetBoardPartStatus
		INTEGER,
	s3EnetBoardNmCntlStatus
		INTEGER,
	s3EnetBoardPsStatus
		INTEGER,
-- the bounded above objects are deprecated
	s3EnetBoardFrmsRxOk
		Counter,
	s3EnetBoardOctetsRxOk
		Counter,
	s3EnetBoardMcastFrmsRxOk
		Counter,
	s3EnetBoardBcastFrmsRxOk
		Counter,
	s3EnetBoardColls
		Counter,
	s3EnetBoardTooLongErrors
		Counter,
	s3EnetBoardRuntErrors
		Counter,
	s3EnetBoardAlignErrors
		Counter,
	s3EnetBoardFcsErrors
		Counter,
	s3EnetBoardLateCollErrors
		Counter
}

s3EnetBoardIndex OBJECT-TYPE
	SYNTAX	INTEGER
	ACCESS	read-only
	STATUS	mandatory
	DESCRIPTION
		"A unique value for each board.  Its value ranges between 1 
		and 12. The value for each board must remain constant at least
 		from one re-initialization of the entity's network management 
		system to the next re-initialization."
	::= { s3EnetBoardEntry 1 }

s3EnetBoardType OBJECT-TYPE
	SYNTAX	INTEGER {
		empty(1),		-- nothing installed
		other(2),		-- none of the following
		m3302(3),		-- Model 3302
		m3304-ST(4),		-- Model 3304-ST
		m3305(5),		-- Model 3305
		m3308(6),		-- Model 3308
		m3313(7),		-- Model 3313
		m3313M(8),		-- Model 3313M
		m3314-ST(9),		-- Model 3314
		m3314M-ST(10),		-- Model 3314M-ST
		m3323(11),		-- Model 3323
		m3324-ST(12),		-- Model 3324-ST
		m3301(16),		-- Model 3301
		m3307(17),		-- Model 3307
		m3356(18),		-- Model 3356
		m3383(24),		-- Model 3383
		m3384(25),		-- Model 3384
		m331x(26),		-- unknown 331x
		m3386(32),		-- Model 3386
		m3394(33),		-- Model 3394
		m3395(34),		-- Model 3395
		m3323S(35),		-- Model 3323S
		m3324S-ST(36),		-- Model 3324S-ST
		m3307A(37),		-- Model 3307A
		m3308A(38)		-- Model 3308A
	}
	ACCESS	read-only
	STATUS	deprecated
	DESCRIPTION
		"See s3SlotModuleType"
	::= { s3EnetBoardEntry 2 }

s3EnetBoardHwVer OBJECT-TYPE
	SYNTAX	INTEGER
	ACCESS	read-only
	STATUS	deprecated
	DESCRIPTION
		"See s3CommonBoardHwVer"
	::= { s3EnetBoardEntry 3 }

s3EnetBoardStatus OBJECT-TYPE
	SYNTAX	INTEGER {
		ok(1),		-- good status
		fail(2)		-- bad status
	}
	ACCESS	read-only
	STATUS	deprecated
	DESCRIPTION
		"See s3CommonBoardStatus"
	::= { s3EnetBoardEntry 4 }

s3EnetBoardReset OBJECT-TYPE
	SYNTAX	INTEGER {
		noReset(1),	-- not resetting
		reset(2)	-- resetting
	}
	ACCESS	read-write
	STATUS	deprecated
	DESCRIPTION
		"See s3CommonBoardReset"
	::= { s3EnetBoardEntry 5 }

s3EnetBoardPartStatus OBJECT-TYPE
	SYNTAX	INTEGER {
		enabled(1),	-- board enabled
		partition(2)	-- board partitioned
	}
	ACCESS	read-write
	STATUS	deprecated
	DESCRIPTION
		"See s3CommonBoardPartStatus"
	::= { s3EnetBoardEntry 6 }

s3EnetBoardNmCntlStatus OBJECT-TYPE
	SYNTAX	INTEGER {
		notNmControl(1),	-- board not under NM control
		nmControl(2)		-- board under NM control
	}
	ACCESS	read-only
	STATUS	deprecated
	DESCRIPTION
		"See s3CommonBoardCntlStatus"
	::= { s3EnetBoardEntry 7 }

s3EnetBoardPsStatus OBJECT-TYPE
	SYNTAX	INTEGER {
		ok(1),		-- good status
		fail(2)		-- bad status
	}
	ACCESS	read-only
	STATUS	deprecated
	DESCRIPTION
		"See s3CommonBoardPsStatus"
	::= { s3EnetBoardEntry 8 }

s3EnetBoardFrmsRxOk OBJECT-TYPE
	SYNTAX	Counter
	ACCESS	read-only
	STATUS	mandatory
	DESCRIPTION
		"This contains a count of frames that are successfully 
		received by the board.  This does not include frames received 
		with a frame-too-long, runt, FCS, or alignment errors. This 
		counter includes broadcast and multicast frames that are 
		received."
	::= { s3EnetBoardEntry 9 }

s3EnetBoardOctetsRxOk OBJECT-TYPE
	SYNTAX	Counter
	ACCESS	read-only
	STATUS	mandatory
	DESCRIPTION
		"Contains a count of data and padding octets in frames that 
		are successfully received by the board.  This does not include
 		frames received with a frame-too-long, runt, FCS, or alignment
 		errors.	This counter includes octets in broadcast and multicast
 		frames that are received. This counter does not include the 
		octets in the address, length/type and CRC fields."
	::= { s3EnetBoardEntry 10 }

s3EnetBoardMcastFrmsRxOk OBJECT-TYPE
	SYNTAX	Counter
	ACCESS	read-only
	STATUS	mandatory
	DESCRIPTION
		"This contains a count of frames that are successfully 
		received by the board and are directed to an active 
		non-broadcast group address.  This does not include frames 
		received with a frame-too-long, runt, FCS, or alignment errors.
		Only frames that are for a multicast address that this 
		interface is receiving are counted. Broadcast packets are not 
		included."
	::= { s3EnetBoardEntry 11 }

s3EnetBoardBcastFrmsRxOk OBJECT-TYPE
	SYNTAX	Counter
	ACCESS	read-only
	STATUS	mandatory
	DESCRIPTION
		"This contains a count of frames that are successfully 
		received by the board and are directed to the broadcast group 
		address. This does not include frames received with a 
		frame-too-long, runt, FCS, or alignment errors.	Multicast 
		packets are not included."
	::= { s3EnetBoardEntry 12 }

s3EnetBoardColls OBJECT-TYPE
	SYNTAX	Counter
	ACCESS	read-only
	STATUS	mandatory
	DESCRIPTION
		"This contains a board level count of the collision flags.  
		This is a summation of all the port level collision flag 
		counters for this board."
	::= { s3EnetBoardEntry 13 }


-- MAC Receive Error Statistics

-- A hierarchical order has been established for those objects listed below 
-- such that when multiple error condition can be associated with one frame, 
-- only one condition is counted.  This hierarchy, in descending order is:
--	frame Too Long
--	runt frames
--	alignment Error
--	frame Check Error


s3EnetBoardTooLongErrors OBJECT-TYPE
	SYNTAX	Counter
	ACCESS	read-only
	STATUS	mandatory
	DESCRIPTION
		"This contains a count of frames that are received by the 
		board and exceed the maximum permitted frame size.  This 
		counter is incremented when the frameTooLong error is 
		detected."
	::= { s3EnetBoardEntry 14 }

s3EnetBoardRuntErrors OBJECT-TYPE
	SYNTAX	Counter
	ACCESS	read-only
	STATUS	mandatory
	DESCRIPTION
		"This contains a count of frames received by the board that 
		are less than the minimum permitted frame size and have a good
		FCS."
	::= { s3EnetBoardEntry 15 }

s3EnetBoardAlignErrors OBJECT-TYPE
	SYNTAX	Counter
	ACCESS	read-only
	STATUS	mandatory
	DESCRIPTION
		"This contains a count of frames received by the board that are
 		not an integral number of octets in length and do not pass the
 		FCS check.  This counter is incremented when the alignmentError
 		status is detected."
	::= { s3EnetBoardEntry 16 }

s3EnetBoardFcsErrors OBJECT-TYPE
	SYNTAX	Counter
	ACCESS	read-only
	STATUS	mandatory
	DESCRIPTION
		"This contains a count of frames received by the board that 
		are an integral number of octets in length that do not pass 
		the FCS check.  This counter is incremented when the 
		frameCheckError status is detected."
	::= { s3EnetBoardEntry 17 }

s3EnetBoardLateCollErrors OBJECT-TYPE
	SYNTAX	Counter
	ACCESS	read-only
	STATUS	mandatory
	DESCRIPTION
		"This contains a count of the board level late collision flags.
  		This is a summation of all the port level late collision flag 
		counters for this board."
	::= { s3EnetBoardEntry 18 }


-- Local Bridge Board Table


s3EnetLocBridgeSlotTable OBJECT-TYPE
	SYNTAX	SEQUENCE OF S3EnetLocBridgeEntry
	ACCESS	not-accessible
	STATUS	mandatory
	DESCRIPTION
		"A table of Local Bridge Board entries.  The number of entries
 		is determined by  the Concentrator Slot Configuration Table.  
		Only those entries that are Ethernet local bridges will have 
		entries in this list."
	::= { s3000EnetLocBridge 1 }

s3EnetLocBridgeEntry OBJECT-TYPE
	SYNTAX	S3EnetLocBridgeEntry
	ACCESS	not-accessible
	STATUS	mandatory
	DESCRIPTION
		"A table containing objects about Boards which are local 
		bridges that are currently plugged into the 3000 chassis."
	INDEX	{ s3EnetLocBridgeIndex }
	::= { s3EnetLocBridgeSlotTable 1 }

S3EnetLocBridgeEntry ::= SEQUENCE {
	s3EnetLocBridgeIndex
		INTEGER,
	s3EnetLocBridgeDescr
		DisplayString,
	s3EnetLocBridgePortCount
		INTEGER,
	s3EnetLocBridgeDiagSts
		OCTET STRING,
	s3EnetLocBridgeBootSts
		INTEGER,
	s3EnetLocBridgeStandbySts
		INTEGER
}

s3EnetLocBridgeIndex OBJECT-TYPE
	SYNTAX	INTEGER
	ACCESS	read-only
	STATUS	mandatory
	DESCRIPTION
		"A unique value for each board.  Its value ranges between 1 
		and 12. The value for each board must remain constant at least
 		from one re-initialization of the entity's network management 
		system to the next re-initialization."
	::= { s3EnetLocBridgeEntry 1 }

s3EnetLocBridgeDescr OBJECT-TYPE
	SYNTAX	DisplayString (SIZE(0..128))
	ACCESS	read-only
	STATUS	mandatory
	DESCRIPTION
		"Description of the local bridge board."
	::= { s3EnetLocBridgeEntry 2 }

s3EnetLocBridgePortCount OBJECT-TYPE
	SYNTAX	INTEGER
	ACCESS	read-only
	STATUS	mandatory
	DESCRIPTION
		"Number of ports that are on the local bridge board."
	::= { s3EnetLocBridgeEntry 3 }

s3EnetLocBridgeDiagSts OBJECT-TYPE
	SYNTAX	OCTET STRING (SIZE(4))
	ACCESS	read-only
	STATUS	mandatory
	DESCRIPTION
		"Latest Diagnostic LED Status that has been recorded."
	::= { s3EnetLocBridgeEntry 4 }

s3EnetLocBridgeBootSts OBJECT-TYPE
	SYNTAX	INTEGER {
		other(1),		-- unknown booting status
		reqstToBoot(2),		-- board is requesting to boot
		notReqstToBoot(3)	-- board is not requesting to boot
	}
	ACCESS	read-only
	STATUS	mandatory
	DESCRIPTION
		"The current status of the board as it relates to rebooting."
	::= { s3EnetLocBridgeEntry 5 }

s3EnetLocBridgeStandbySts OBJECT-TYPE
	SYNTAX	INTEGER {
		other(1),		-- unknown booting status
		standby(2), 		-- bridge is in standby mode
		notStandby(3)		-- bridge is operational and not standby
	}
	ACCESS	read-only
	STATUS	mandatory
	DESCRIPTION
		"This status says whether the local bridge is active or in 
		standby mode."
	::= { s3EnetLocBridgeEntry 6 }



-- Local Bridge Port Table


s3EnetLocBridgePortTable OBJECT-TYPE
	SYNTAX	SEQUENCE OF S3EnetLocBridgePortEntry
	ACCESS	not-accessible
	STATUS	mandatory
	DESCRIPTION
		"A table of Port entries that are part of a local bridge.  The 
		number of entries is determined by knowing the number of local 
		bridge boards that are installed by looking at 
		s3ChassisSlotConfigTable and by knowing how many ports are on 
		a local bridge board by looking at s3EnetLocBridgePortCount."
	::= { s3000EnetLocBridge 2 }

s3EnetLocBridgePortEntry OBJECT-TYPE
	SYNTAX	S3EnetLocBridgePortEntry
	ACCESS	not-accessible
	STATUS	mandatory
	DESCRIPTION
		"A table containing objects about the ports of the local 
		bridges that are currently plugged into the 3000 chassis."
	INDEX	{ s3EnetLocBridgePortSlotIndex, s3EnetLocBridgePortIndex }
	::= { s3EnetLocBridgePortTable 1 }

S3EnetLocBridgePortEntry ::= SEQUENCE {
	s3EnetLocBridgePortSlotIndex
		INTEGER,
	s3EnetLocBridgePortIndex
		INTEGER,
	s3EnetLocBridgePortMdaId
		INTEGER,
	s3EnetLocBridgePortIf
		INTEGER,
	s3EnetLocBridgePortDescr
		DisplayString,
	s3EnetLocBridgePortOpSts
		INTEGER
}

s3EnetLocBridgePortSlotIndex OBJECT-TYPE
	SYNTAX	INTEGER
	ACCESS	read-only
	STATUS	mandatory
	DESCRIPTION
		"A unique value for each board.  Its value ranges between 1 
		and 12. The value for each board must remain constant at least
 		from one re-initialization of the entity's network management 
		system to the next re-initialization."
	::= { s3EnetLocBridgePortEntry 1 }

s3EnetLocBridgePortIndex OBJECT-TYPE
	SYNTAX	INTEGER
	ACCESS	read-only
	STATUS	mandatory
	DESCRIPTION
		"A unique value for each port.  Its value ranges between 1 and
 		12. The value for each port must remain constant at least from
 		one reinitialization of the entity's network management system
 		to the next reinitialization."
	::= { s3EnetLocBridgePortEntry 2 }

s3EnetLocBridgePortMdaId OBJECT-TYPE
	SYNTAX	INTEGER
	ACCESS	read-only
	STATUS	mandatory
	DESCRIPTION
		"Medium dependent ID for the port."
	::= { s3EnetLocBridgePortEntry 3 }

s3EnetLocBridgePortIf OBJECT-TYPE
	SYNTAX	INTEGER {
		other(1),		-- unknown interfaces
		etherEther(2),		-- ethernet to ethernet bridge
		etherTokenRing(3)	-- ethernet to token ring bridge
	}
	ACCESS	read-only
	STATUS	mandatory
	DESCRIPTION
		"Bridge interface types."
	::= { s3EnetLocBridgePortEntry 4 }

s3EnetLocBridgePortDescr OBJECT-TYPE
	SYNTAX	DisplayString (SIZE(0..128))
	ACCESS	read-only
	STATUS	mandatory
	DESCRIPTION
		"A text description of the port."
	::= { s3EnetLocBridgePortEntry 5 }

s3EnetLocBridgePortOpSts OBJECT-TYPE
	SYNTAX	INTEGER {
		other(1),
		standby(2),
		notStandby(3)
	}
	ACCESS	read-only
	STATUS	mandatory
	DESCRIPTION
		"Operating status of the port."
	::= { s3EnetLocBridgePortEntry 6 }


-- Remote Bridge Board Table


s3EnetRemBridgeSlotTable OBJECT-TYPE
	SYNTAX	SEQUENCE OF S3EnetRemBridgeEntry
	ACCESS	not-accessible
	STATUS	mandatory
	DESCRIPTION
		"A table of Remote Bridge Board entries.  The number of 
		entries is determined by the Concentrator Slot Configuration 
		Table. Only those entries that are Ethernet remote bridges will
 		have entries in this list."
	::= { s3000EnetRemBridge 1 }

s3EnetRemBridgeEntry OBJECT-TYPE
	SYNTAX	S3EnetRemBridgeEntry
	ACCESS	not-accessible
	STATUS	mandatory
	DESCRIPTION
		"A table containing objects about Boards which are remote 
		bridges that are currently plugged into the 3000 chassis."
	INDEX	{ s3EnetRemBridgeIndex }
	::= { s3EnetRemBridgeSlotTable 1 }

S3EnetRemBridgeEntry ::= SEQUENCE {
	s3EnetRemBridgeIndex
		INTEGER,
	s3EnetRemBridgeDescr
		DisplayString ,
	s3EnetRemBridgePortCount
		INTEGER,
	s3EnetRemBridgeDiagSts
		OCTET STRING,
	s3EnetRemBridgeBootSts
		INTEGER,
	s3EnetRemBridgeStandbySts
		INTEGER
}

s3EnetRemBridgeIndex OBJECT-TYPE
	SYNTAX	INTEGER
	ACCESS	read-only
	STATUS	mandatory
	DESCRIPTION
		"A unique value for each board.  Its value ranges between 1 
		and 12. The value for each board must remain constant at least
 		from one re-initialization of the entity's network management 
		system to the next re-initialization."
	::= { s3EnetRemBridgeEntry 1 }

s3EnetRemBridgeDescr OBJECT-TYPE
	SYNTAX	DisplayString (SIZE(0..128))
	ACCESS	read-only
	STATUS	mandatory
	DESCRIPTION
		"Description of the board."
	::= { s3EnetRemBridgeEntry 2 }

s3EnetRemBridgePortCount OBJECT-TYPE
	SYNTAX	INTEGER
	ACCESS	read-only
	STATUS	mandatory
	DESCRIPTION
		"Number of ports that are on the board."
	::= { s3EnetRemBridgeEntry 3 }

s3EnetRemBridgeDiagSts OBJECT-TYPE
	SYNTAX	OCTET STRING (SIZE(4))
	ACCESS	read-only
	STATUS	mandatory
	DESCRIPTION
		"Latest Diagnostic LED Status that has been recorded."
	::= { s3EnetRemBridgeEntry 4 }

s3EnetRemBridgeBootSts OBJECT-TYPE
	SYNTAX	INTEGER {
		other(1),		-- unknown booting status
		reqstToBoot(2),		-- board is requesting to boot
		notReqstToBoot(3)	-- board is not requesting to boot
	}
	ACCESS	read-only
	STATUS	mandatory
	DESCRIPTION
		"The current status of the board as it relates to rebooting."
	::= { s3EnetRemBridgeEntry 5 }

s3EnetRemBridgeStandbySts OBJECT-TYPE
	SYNTAX	INTEGER {
		other(1),	-- unknown booting status
		standby(2),	-- remote bridge is in standby mode
		notStandby(3)	-- remote bridge is active not in standby
	}
	ACCESS	read-only
	STATUS	mandatory
	DESCRIPTION
		"This status says whether the remote bridge is active or in 
		standby mode."
	::= { s3EnetRemBridgeEntry 6 }



-- Remote Bridge Port Table


s3EnetRemBridgePortTable OBJECT-TYPE
	SYNTAX	SEQUENCE OF S3EnetRemBridgePortEntry
	ACCESS	not-accessible
	STATUS	mandatory
	DESCRIPTION
		"A table of Port entries that are part of a remote bridge.  
		The number of entries is determined by knowing the number of 
		remote bridge boards that are installed by looking at 
		s3ChassisSlotConfigTable and by knowing how many ports are on 
		a remote bridge board by looking at s3EnetRemBridgePortCount."
	::= { s3000EnetRemBridge 2 }

s3EnetRemBridgePortEntry OBJECT-TYPE
	SYNTAX	S3EnetRemBridgePortEntry
	ACCESS	not-accessible
	STATUS	mandatory
	DESCRIPTION
		"A table containing objects about the ports of the remote 
		bridges that are currently plugged into the 3000 chassis."
	INDEX	{ s3EnetRemBridgePortSlotIndex,
			 s3EnetRemBridgePortIndex }
	::= { s3EnetRemBridgePortTable 1 }

S3EnetRemBridgePortEntry ::= SEQUENCE {
	s3EnetRemBridgePortSlotIndex
		INTEGER,
	s3EnetRemBridgePortIndex
		INTEGER,
	s3EnetRemBridgePortMdaId
		INTEGER,
	s3EnetRemBridgePortDescr
		DisplayString,
	s3EnetRemBridgePortOpSts
		INTEGER,
	s3EnetRemBridgePortRdySnd
		INTEGER,
	s3EnetRemBridgePortClrSnd
		INTEGER,
	s3EnetRemBridgePortCarDt
		INTEGER
}

s3EnetRemBridgePortSlotIndex OBJECT-TYPE
	SYNTAX	INTEGER
	ACCESS	read-only
	STATUS	mandatory
	DESCRIPTION
		"A unique value for each board.  Its value ranges between 1 
		and 12. The value for each board must remain constant at least
 		from one re-initialization of the entity's network management 
		system to the next re-initialization."
	::= { s3EnetRemBridgePortEntry 1 }

s3EnetRemBridgePortIndex OBJECT-TYPE
	SYNTAX	INTEGER
	ACCESS	read-only
	STATUS	mandatory
	DESCRIPTION
		"A unique value for each port.  Its value ranges between 1 and
 		12. The	value for each port must remain constant at least from
 		one re-	initialization of the entity's network management 
		system to the next re-initialization."
	::= { s3EnetRemBridgePortEntry 2 }

s3EnetRemBridgePortMdaId OBJECT-TYPE
	SYNTAX	INTEGER {
		other(1),
		ethernet(2),
		x21Barrier(3),
		x21Unbarrier(4),
		rs232(5),
		rs449(6),
		v35(7),
		g703(8),
		t1(9)
	}
	ACCESS	read-only
	STATUS	mandatory
	DESCRIPTION
		"Medium dependent ID for the port."
	::= { s3EnetRemBridgePortEntry 3 }

s3EnetRemBridgePortDescr OBJECT-TYPE
	SYNTAX	DisplayString (SIZE(0..128))
	ACCESS	read-only
	STATUS	mandatory
	DESCRIPTION
		"A text description of the port."
	::= { s3EnetRemBridgePortEntry 4 }

s3EnetRemBridgePortOpSts OBJECT-TYPE
	SYNTAX	INTEGER {
		other(1),
		standby(2),
		operational(3),
		noLink(4)
	}
	ACCESS	read-only
	STATUS	mandatory
	DESCRIPTION
		"Operating status of the port."
	::= { s3EnetRemBridgePortEntry 5 }

s3EnetRemBridgePortRdySnd OBJECT-TYPE
	SYNTAX	INTEGER {
		other(1),		-- unknown status
		rdySnd(2),		-- ready to send
		notRdySnd(3)		-- not ready to send
	}
	ACCESS	read-only
	STATUS	mandatory
	DESCRIPTION
		"Ready to send status of the port."
	::= { s3EnetRemBridgePortEntry 6 }

s3EnetRemBridgePortClrSnd OBJECT-TYPE
	SYNTAX	INTEGER {
		other(1),		-- unknown status
		clrSnd(2),		-- clear to send
		notClrSnd(3)		-- not clear to send
	}
	ACCESS	read-only
	STATUS	mandatory
	DESCRIPTION
		"Clear to send status of the port."
	::= { s3EnetRemBridgePortEntry 7 }

s3EnetRemBridgePortCarDt OBJECT-TYPE
	SYNTAX	INTEGER {
		other(1),		-- unknown status
		carDt(2),		-- carrier detected
		noCarDt(3)		-- no carrier detected
	}
	ACCESS	read-only
	STATUS	mandatory
	DESCRIPTION
		"Carrier detect status of the port."
	::= { s3EnetRemBridgePortEntry 8 }



-- Router Board Table


s3EnetRouterSlotTable OBJECT-TYPE
	SYNTAX	SEQUENCE OF S3EnetRouterEntry
	ACCESS	not-accessible
	STATUS	mandatory
	DESCRIPTION
		"A table of Router Board entries.  The number of entries is 
		determined by the Concentrator Slot Configuration Table.  
		Only those entries that are Ethernet routers will have entries
 		in this list."
	::= { s3000EnetRouter 1 }

s3EnetRouterEntry OBJECT-TYPE
	SYNTAX	S3EnetRouterEntry
	ACCESS	not-accessible
	STATUS	mandatory
	DESCRIPTION
		"A table containing objects about Boards which are routers 
		that are currently plugged into the 3000 chassis."
	INDEX	{ s3EnetRouterIndex }
	::= { s3EnetRouterSlotTable 1 }

S3EnetRouterEntry ::= SEQUENCE {
	s3EnetRouterIndex
		INTEGER,
	s3EnetRouterDescr
		DisplayString,
	s3EnetRouterDiagSts
		OCTET STRING,
	s3EnetRouterStandbySts
		INTEGER
}

s3EnetRouterIndex OBJECT-TYPE
	SYNTAX	INTEGER
	ACCESS	read-only
	STATUS	mandatory
	DESCRIPTION
		"A unique value for each board.  Its value ranges between 1 
		and 12. The value for each board must remain constant at 
		least from one re-initialization of the entity's network 
		management system to the next re-initialization."
	::= { s3EnetRouterEntry 1 }

s3EnetRouterDescr OBJECT-TYPE
	SYNTAX	DisplayString (SIZE(0..128))
	ACCESS	read-only
	STATUS	mandatory
	DESCRIPTION
		"Description of the router board."
	::= { s3EnetRouterEntry 2 }

s3EnetRouterDiagSts OBJECT-TYPE
	SYNTAX	OCTET STRING (SIZE(4))
	ACCESS	read-only
	STATUS	mandatory
	DESCRIPTION
		"Latest Diagnostic LED Status that has been recorded."
	::= { s3EnetRouterEntry 3 }

s3EnetRouterStandbySts OBJECT-TYPE
	SYNTAX	INTEGER {
		other(1),	-- unknown booting status
		standby(2),	-- router is in standby mode
		notStandby(3)	-- router is operational, not in standby
	}
	ACCESS	read-only
	STATUS	mandatory
	DESCRIPTION
		"This status says whether the router is active or in standby 
		mode."
	::= { s3EnetRouterEntry 4 }



-- Port Table


s3EnetPortTable OBJECT-TYPE
	SYNTAX	SEQUENCE OF S3EnetPortEntry
	ACCESS	not-accessible
	STATUS	mandatory
	DESCRIPTION
		"A list of port entries.  The number of entries is given by 
		learning the type of board from the information in the 
		s3ChassisSlotConfigTable."
	::= { s3000EnetPort 1 }

s3EnetPortEntry OBJECT-TYPE
	SYNTAX	S3EnetPortEntry
	ACCESS	not-accessible
	STATUS	mandatory
	DESCRIPTION
		"A table containing objects about the Ports of each board 
		plugged into the 3000 chassis."
	INDEX	{ s3EnetPortBoardIndex, s3EnetPortIndex }
	::= { s3EnetPortTable 1 }

S3EnetPortEntry ::= SEQUENCE {
	s3EnetPortBoardIndex
		INTEGER,
	s3EnetPortIndex
		INTEGER,
	s3EnetPortLinkStatus
		INTEGER,
	s3EnetPortPartStatus
		INTEGER,
	s3EnetPortJabberStatus
		INTEGER,
	s3EnetPortFrmsRxOk
		Counter,
	s3EnetPortOctetsRxOk
		Counter,
	s3EnetPortMcastFrmsRxOk
		Counter,
	s3EnetPortBcastFrmsRxOk
		Counter,
	s3EnetPortColls
		Counter,
	s3EnetPortTooLongErrors
		Counter,
	s3EnetPortRuntErrors
		Counter,
	s3EnetPortAlignErrors
		Counter,
	s3EnetPortFcsErrors
		Counter,
	s3EnetPortLateCollErrors
		Counter,
	s3EnetPortMDIXSwitch
		INTEGER
	}

s3EnetPortBoardIndex OBJECT-TYPE
	SYNTAX	INTEGER
	ACCESS	read-only
	STATUS	mandatory
	DESCRIPTION
		"A unique value for each board.  Its value ranges between 1 and
		12.  The value for each board must remain constant at
		least from one reinitialization of the entity's network
		management system to the next reinitialization."
	::= { s3EnetPortEntry 1 }

s3EnetPortIndex OBJECT-TYPE
	SYNTAX	INTEGER
	ACCESS	read-only
	STATUS	mandatory
	DESCRIPTION
		"A unique value for each port.  Its value is dependent on the
		board type.  The value for each port must remain constant
		at least from one reinitialization of the entity's network
		management system to the next reinitialization."
	::= { s3EnetPortEntry 2 }

s3EnetPortLinkStatus OBJECT-TYPE
	SYNTAX	INTEGER {
		off(1),		-- link is not connected
		on(2),		-- link is connected
		other(3)	-- returned for AUI
	}
	ACCESS	read-only
	STATUS	mandatory
	DESCRIPTION
		"Tells whether the port is receiving link status."
	::= { s3EnetPortEntry 3 }

s3EnetPortPartStatus OBJECT-TYPE
	SYNTAX	INTEGER {
		enabled(1),		-- port enabled
		partition(2),		-- port partitioned
		autoPartition(3)	-- port auto-partitioned
	}
	ACCESS	read-write
	STATUS	mandatory
	DESCRIPTION
		"This indicates the operational status of the Port.  Writing a partition(2) 
		will partition the port indefinitely and enabled(1) will enable the port."
	::= { s3EnetPortEntry 4 }

s3EnetPortJabberStatus OBJECT-TYPE
	SYNTAX	INTEGER {
		ok(1),	
		jabbering(2)	-- Port receiving jabber
	}
	ACCESS	read-only
	STATUS	mandatory
	DESCRIPTION
		"Tells whether the DTE connected to the Port is jabbering or 
		not."
	::= { s3EnetPortEntry 5 }

s3EnetPortFrmsRxOk OBJECT-TYPE
	SYNTAX	Counter
	ACCESS	read-only
	STATUS	mandatory
	DESCRIPTION
		"This contains a count of frames that are successfully 
		received by the port.  This does not include frames received 
		with a frame-too-long, runt, FCS, or alignment errors. This 
		counter includes broadcast and multicast frames that are 
		received."
	::= { s3EnetPortEntry 6 }

s3EnetPortOctetsRxOk OBJECT-TYPE
	SYNTAX	Counter
	ACCESS	read-only
	STATUS	mandatory
	DESCRIPTION
		"Contains a count of data and padding octets in frames that 
		are successfully received by the port.  This does not include 
		frames received with a frame-too-long, runt, FCS, or 
		alignment errors. This counter includes octets in broadcast 
		and multicast frames that are received. This counter does not 
		include the octets in the address, length/type and CRC fields."
	::= { s3EnetPortEntry 7 }

s3EnetPortMcastFrmsRxOk OBJECT-TYPE
	SYNTAX	Counter
	ACCESS	read-only
	STATUS	mandatory
	DESCRIPTION
		"This contains a count of frames that are successfully 
		received by the port and are directed to an active 
		non-broadcast group address.  This does not include frames 
		received with a frame-too-long, runt, FCS, or alignment errors.
		Only frames that are for a multicast address that this 
		interface is receiving are counted. Broadcast packets are not 
		included."
	::= { s3EnetPortEntry 8 }

s3EnetPortBcastFrmsRxOk OBJECT-TYPE
	SYNTAX	Counter
	ACCESS	read-only
	STATUS	mandatory
	DESCRIPTION
		"This contains a count of frames that are successfully 
		received by the port and are directed to the broadcast group 
		address. This does not include frames received with a 
		frame-too-long, runt, FCS, or alignment errors.	Multicast 
		packets are not included."
	::= { s3EnetPortEntry 9 }

s3EnetPortColls OBJECT-TYPE
	SYNTAX	Counter
	ACCESS	read-only
	STATUS	mandatory
	DESCRIPTION
		"This contains a count of the collision flags."
	::= { s3EnetPortEntry 10 }


-- Port MAC Error Statistics

-- A hierarchical order has been established for those objects listed below 
-- such that when multiple error conditions can be associated with one frame, 
-- only one condition is counted.  This hierarchy, in descending order is:
--	frame too long
--	runt frames
--	alignment error
--	frame check error


s3EnetPortTooLongErrors OBJECT-TYPE
	SYNTAX	Counter
	ACCESS	read-only
	STATUS	mandatory
	DESCRIPTION
		"This contains a count of frames that are received by the port 
		and exceed the maximum permitted frame size.  This counter is 
		incremented when the frameTooLong error is detected."
	::= { s3EnetPortEntry 11 }

s3EnetPortRuntErrors OBJECT-TYPE
	SYNTAX	Counter
	ACCESS	read-only
	STATUS	mandatory
	DESCRIPTION
		"This contains a count of frames received by the port that are
 		less than the minimum permitted frame size and have a good 
		FCS."
	::= { s3EnetPortEntry 12 }

s3EnetPortAlignErrors OBJECT-TYPE
	SYNTAX	Counter
	ACCESS	read-only
	STATUS	mandatory
	DESCRIPTION
		"This contains a count of frames received by the port that 
		are not an integral number of octets in length and do not 
		pass the FCS check. This counter is incremented when the 
		alignmentError status is detected."
	::= { s3EnetPortEntry 13 }

s3EnetPortFcsErrors OBJECT-TYPE
	SYNTAX	Counter
	ACCESS	read-only
	STATUS	mandatory
	DESCRIPTION
		"This contains a count of frames received the port that are 
		an integral number of octets in length that do not pass the 
		FCS check.  This counter is incremented when the 
		frameCheckError status is detected."
	::= { s3EnetPortEntry 14 }

s3EnetPortLateCollErrors OBJECT-TYPE
	SYNTAX	Counter
	ACCESS	read-only
	STATUS	mandatory
	DESCRIPTION
		"This contains a count of the port level late collision flags."
	::= { s3EnetPortEntry 15 }

s3EnetPortMDIXSwitch OBJECT-TYPE
	SYNTAX	INTEGER {
		other(1),	-- unknown or other
		tenBaseT(2),	-- 10BASE-T, "normal" or MDI-X
		tenBaseTMdi(3)	-- 10BASE-T, switched to MDI
	}
	ACCESS	read-only
	STATUS	mandatory
	DESCRIPTION
		"This tells whether the MDI-X/MDI switch for the port is set 
		to MDI-X or MDI position.  If the port has an associated 
		MDI-X/MDI switch, then the agent will return the current 
		setting.  If the port does not have the	switch, then other(1) 
		will be returned."
	::= { s3EnetPortEntry 19 }

-- SECTION 3: Network Management Module Group

-- The Network Management Module Group consists of Module Group,
-- EEPROM Configuration Group, Hardware Configuration Group, Trap
-- Server Table, and Authentication Trap Control.
--
-- All of these groups are DEPRECATED!


-- Module Group

s3EnetNmmType OBJECT-TYPE
	SYNTAX	INTEGER {
		other(1),		-- none of the following
		m3313(2),		-- Model 3313
		m3313M(3),		-- Model 3313M
		m3314-ST(4),		-- Model 3314-ST
		m3314M-ST(5),		-- Model 3314M-ST
		m3138(6)		-- Model 3138
	}
	ACCESS	read-only
	STATUS	deprecated
	DESCRIPTION
		"See s3AgentType"
	::= { s3000EnetNmm 1 }

s3EnetNmmMdaHwVer OBJECT-TYPE
	SYNTAX	INTEGER
	ACCESS	read-only
	STATUS	deprecated
	DESCRIPTION
		"See AgentMdaHwVer"
	::= { s3000EnetNmm 2 }

s3EnetNmmFwVer OBJECT-TYPE
	SYNTAX	INTEGER
	ACCESS	read-only
	STATUS	deprecated
	DESCRIPTION
		"See s3AgentFwVer"
	::= { s3000EnetNmm 3 }

s3EnetNmmSwMajorVer OBJECT-TYPE
	SYNTAX	INTEGER
	ACCESS	read-only
	STATUS	deprecated
	DESCRIPTION
		"See s3AgentSwMajor"
	::= { s3000EnetNmm 4 }

s3EnetNmmSwMinorVer OBJECT-TYPE
	SYNTAX	INTEGER
	ACCESS	read-only
	STATUS	deprecated
	DESCRIPTION
		"See s3AgentSwMinor"
	::= { s3000EnetNmm 5 }

s3EnetNmmStatus OBJECT-TYPE
	SYNTAX	INTEGER {
		offline(1),	-- the nmm is offline
		online(2)	-- the nmm is online
	}
	ACCESS	read-only
	STATUS	deprecated
	DESCRIPTION
		"See s3AgentStatus"
	::= { s3000EnetNmm 6 }

s3EnetNmmMode OBJECT-TYPE
	SYNTAX	INTEGER {
		primary(1),	-- in primary mode
		secondary(2)	-- in secondary mode
	}
	ACCESS	read-write
	STATUS	deprecated
	DESCRIPTION
		"See s3AgentMode"
	::= { s3000EnetNmm 7 }

s3EnetNmmReset OBJECT-TYPE
	SYNTAX	INTEGER {
		notreset(1),	-- not reseting
		reset(2)	-- reset
	}
	ACCESS	read-write
	STATUS	deprecated
	DESCRIPTION
		"See s3AgentReset"
	::= { s3000EnetNmm 8 }

s3EnetNmmRestart OBJECT-TYPE
	SYNTAX	INTEGER {
		notrestart(1),	-- not restarting
		restart(2)	-- restart
	}
	ACCESS	read-write
	STATUS	deprecated
	DESCRIPTION
		"See s3AgentRestart"
	::= { s3000EnetNmm 9 }



-- EEPROM Configuration Group

s3EnetNmmIpAddr OBJECT-TYPE
	SYNTAX	IpAddress
	ACCESS	read-write
	STATUS	deprecated
	DESCRIPTION
		"See s3AgentIpAddr"
	::= { s3000EnetNmm 10 }

s3EnetNmmNetMask OBJECT-TYPE
	SYNTAX	IpAddress
	ACCESS	read-write
	STATUS	deprecated
	DESCRIPTION
		"See s3AgentNetMask"
	::= { s3000EnetNmm 11 }

s3EnetNmmDefaultGateway OBJECT-TYPE
	SYNTAX	IpAddress
	ACCESS	read-write
	STATUS	deprecated
	DESCRIPTION
		"See s3AgentDefaultGateway"
	::= { s3000EnetNmm 12 }

s3EnetNmmFileServerAddr OBJECT-TYPE
	SYNTAX	IpAddress
	ACCESS	read-write
	STATUS	deprecated
	DESCRIPTION
		"See s3AgentBootServerAddr"
	::= { s3000EnetNmm 13 }

s3EnetNmmBootFilePath OBJECT-TYPE
	SYNTAX	DisplayString (SIZE(0..64))
	ACCESS	read-write
	STATUS	deprecated
	DESCRIPTION
		"See s3AgentBootFile"
	::= { s3000EnetNmm 14 }

s3EnetNmmBootMode OBJECT-TYPE
	SYNTAX	INTEGER {
		eeprom(1),	-- get boot info from eeprom
		bootp(2)	-- get boot info from bootp
	}
	ACCESS	read-write
	STATUS	deprecated
	DESCRIPTION
		"See s3AgentBootMode"
	::= { s3000EnetNmm 15 }

s3EnetNmmWriteEeprom OBJECT-TYPE
	SYNTAX	INTEGER {
		notWriteEeprom(1),	-- not writing EEPROM 
		writeEeprom(2)		-- write EEPROM
	}
	ACCESS	read-write
	STATUS	deprecated
	DESCRIPTION
		"See s3AgentWriteEeprom"
	::= { s3000EnetNmm 16 }



-- Hardware Configuration Group

s3EnetNmmBaudRate OBJECT-TYPE
	SYNTAX	Gauge
	ACCESS	read-only
	STATUS	deprecated
	DESCRIPTION
		"See s3AgentBaudRate"
	::= { s3000EnetNmm 17 }

s3EnetNmmInitString OBJECT-TYPE
	SYNTAX	OCTET STRING (SIZE(0..64))
	ACCESS	read-write
	STATUS	deprecated
	DESCRIPTION
		"See s3AgentInitString"
	::= { s3000EnetNmm 18 }

s3EnetNmmLocation OBJECT-TYPE
	SYNTAX	DisplayString (SIZE(0..64))
	ACCESS	read-write
	STATUS	deprecated
	DESCRIPTION
		"See s3AgentLocation"
	::= { s3000EnetNmm 19 }



-- Trap Server Table

s3EnetNmmTrapServerTable OBJECT-TYPE
	SYNTAX	SEQUENCE OF S3EnetNmmTrapServerEntry
	ACCESS	not-accessible
	STATUS	deprecated
	DESCRIPTION
		"See s3AgentReceiverTable"
	::= { s3000EnetNmm 20 }

s3EnetNmmTrapServerEntry OBJECT-TYPE
	SYNTAX	S3EnetNmmTrapServerEntry
	ACCESS	not-accessible
	STATUS	deprecated
	DESCRIPTION
		"See s3AgentTrapReceiverEntry"
	INDEX	{ s3EnetNmmTrapServerAddress }
	::= { s3EnetNmmTrapServerTable 1 }

S3EnetNmmTrapServerEntry ::= SEQUENCE {
	s3EnetNmmTrapType
		INTEGER,
	s3EnetNmmTrapServerAddress
		IpAddress,
	s3EnetNmmTrapServerComm
		OCTET STRING
}

s3EnetNmmTrapType OBJECT-TYPE
	SYNTAX	INTEGER {
		other (1),	-- none of the following
		invalid (2)	-- an invalidated address
	}
	ACCESS	read-write
	STATUS	deprecated
	DESCRIPTION
		"See s3AgentTrapRcvrStatus"
	::= { s3EnetNmmTrapServerEntry 1 }

s3EnetNmmTrapServerAddress OBJECT-TYPE
	SYNTAX	IpAddress
	ACCESS	read-write
	STATUS	deprecated
	DESCRIPTION
		"See s3AgentTrapRcvrNetAddress"
	::= { s3EnetNmmTrapServerEntry 2 }

s3EnetNmmTrapServerComm OBJECT-TYPE
	SYNTAX	OCTET STRING (SIZE(0..20))
	ACCESS	read-write
	STATUS	deprecated
	DESCRIPTION
		"See s3AgentTrapRcvrComm"
	::= { s3EnetNmmTrapServerEntry 3 }

-- Authentication Trap Control

s3EnetNmmAuthTrap OBJECT-TYPE
	SYNTAX	INTEGER {
		disable(1),	-- disable authentication traps
		enable(2)	-- enable authentication traps
	}
	ACCESS	read-write
	STATUS	deprecated
	DESCRIPTION
		"See s3AgentAuthTrap"
	::= { s3000EnetNmm 21 }

END


-- file:  ieee802.3-1.0-09.30.91

SYNOPTICS-IEEE8023-MIB

-- IEEE 802.3 MIB Release 1.0
-- DRAFT Revision 9/30/91
-- Printed 10/7/91

-- Copyright 1991 SynOptics Communications, Inc.  All Rights
-- Reserved.  Reproduction of this document is authorized on
-- condition that the foregoing copyright notice is included.
-- This SynOptics SNMP Management Information Base Specification
-- (Specification) embodies SynOptics' confidential and
-- proprietary intellectual property.  SynOptics retains all
-- title and ownership in the Specification, including any
-- revisions.  
--
-- It is SynOptics intent to encourage the widespread use of
-- this Specification in connection with the management of
-- SynOptics products. SynOptics grants vendors, end-users,
-- and other interested parties a non-exclusive license to
-- use this Specification in connection with the management
-- of SynOptics products.
--
-- This Specification is supplied "AS IS," and SynOptics makes
-- no warranty, either express or implied, as to the use,
-- operation, condition, or performance of the Specification.

DEFINITIONS ::= BEGIN

-- SECTION 1: Top Level Definitions

-- Imports

IMPORTS
	Counter		FROM RFC1155-SMI
	PhysAddress	FROM RFC1213-MIB
	OBJECT-TYPE	FROM RFC-1212
	ieee8023	FROM SYNOPTICS-COMMON-MIB;


-- SECTION 2: IEEE 802.3 Interface Statistics Table

ieee8023IfTable OBJECT-TYPE
	SYNTAX	SEQUENCE OF Ieee8023IfEntry
	ACCESS	not-accessible
	STATUS	mandatory
	DESCRIPTION
		"Statistics for a list of interface entries. There is one 
		entry per IEEE 802.3 like 'interface.'"
	::= { ieee8023 1 }

ieee8023IfEntry OBJECT-TYPE
	SYNTAX	Ieee8023IfEntry
	ACCESS	not-accessible
	STATUS	mandatory
	INDEX	{ ieee8023IfIndex }
	::= { ieee8023IfTable 1 }

Ieee8023IfEntry ::= SEQUENCE {
	ieee8023IfIndex
		INTEGER,
	ieee8023FrmsTxOk
		Counter,
	ieee8023SingleCollFrms
		Counter,
	ieee8023MultipleCollFrms
		Counter,
	ieee8023OctetsTxOk
		Counter,
	ieee8023DefTx
		Counter,
	ieee8023McastFrmsTxOk
		Counter,
	ieee8023BcastFrmsTxOk
		Counter,
	ieee8023LateColls
		Counter,
	ieee8023ExcessColls
		Counter,
	ieee8023IntlMacTxError
		Counter,
	ieee8023CsErrors
		Counter,
	ieee8023ExcessDef
		Counter,
	ieee8023FrmsRxOk
		Counter,
	ieee8023OctetsRxOk
		Counter,
	ieee8023McastFrmsRxOk
		Counter,
	ieee8023BcastFrmsRxOk
		Counter,
	ieee8023TooLongErrors
		Counter,
	ieee8023AlignErrors
		Counter,
	ieee8023FcsErrors
		Counter,
	ieee8023IrLengthErrors
		Counter,
	ieee8023OorLengthFields
		Counter,
	ieee8023IntlMacRxErrors
		Counter,
	ieee8023InitMac
		INTEGER,
	ieee8023PromRxStatus
		INTEGER,
	ieee8023MacSubLayerStatus
		INTEGER,
	ieee8023TxStatus
		INTEGER,
	ieee8023McastRxStatus
		INTEGER,
	ieee8023MacAddress
		PhysAddress,
	ieee8023SqeTestErrors
		Counter
	}

ieee8023IfIndex OBJECT-TYPE
	SYNTAX	INTEGER
	ACCESS	read-only
	STATUS	mandatory
	DESCRIPTION
		"Index of the interface.  The interface identified by a
		particular value of this index is the same interface as
		identified by the same value of ifIndex."
	::= { ieee8023IfEntry 1 }

ieee8023FrmsTxOk OBJECT-TYPE
	SYNTAX	Counter
	ACCESS	read-only
	STATUS	mandatory
	DESCRIPTION
		"The number of frames that are successfully transmitted.
		This counter is incremented when a frame is successfully
		transmitted, even if one of the collision counters (following
		two objects) is also counted. In other words, this count
		includes transmissions that succeeded after some number of
		collisions. This count includes multicast and broadcast 
		frames."
	::= { ieee8023IfEntry 2 }

ieee8023SingleCollFrms OBJECT-TYPE
	SYNTAX	Counter
	ACCESS	read-only
	STATUS	mandatory
	DESCRIPTION
		"The number of frames that are involved in a single collision,
		and are subsequently transmitted successfully. If this counter 
		is incremented, then the ieee8023FrmsTxOK count will also be 
		incremented AND ieee8023MultipleCollFrms will NOT be 
		incremented."
	::= { ieee8023IfEntry 3 }

ieee8023MultipleCollFrms OBJECT-TYPE
	SYNTAX	Counter
	ACCESS	read-only
	STATUS	mandatory
	DESCRIPTION
		"The number of frames that are involved in more than one
		collision and are subsequently transmitted successfully.
		If this counter is incremented, then the ieee8023FrmsTxOK
		count will also be incremented AND ieee8023SingleCollFrms will
		NOT be incremented."
	::= { ieee8023IfEntry 4 }

ieee8023OctetsTxOk OBJECT-TYPE
	SYNTAX	Counter
	ACCESS	read-only
	STATUS	mandatory
	DESCRIPTION
		"The amount of data AND PADDING octets of frames that are
		successfully transmitted. This counter includes octets in 
		broadcast and multicast frames that are transmitted.
		This count does not include the address fields, length/type
		field, and CRC field of the frame. According to Ethernet
		terminology, it is purely the data field (IP header, etc.)."
	::= { ieee8023IfEntry 5 }

ieee8023DefTx OBJECT-TYPE
	SYNTAX	Counter
	ACCESS	read-only
	STATUS	mandatory
	DESCRIPTION
		"The number of frames whose transmission was delayed on its
		first attempt because the medium was busy. Frames involved in
		collisions are NOT included in this count."
	::= { ieee8023IfEntry 6 }

ieee8023McastFrmsTxOk OBJECT-TYPE
	SYNTAX	Counter
	ACCESS	read-only
	STATUS	mandatory
	DESCRIPTION
		"The number of frames successfully transmitted to a multicast
		address. This counter does not include frames sent to the
		broadcast address."
	::= { ieee8023IfEntry 7 }

ieee8023BcastFrmsTxOk OBJECT-TYPE
	SYNTAX	Counter
	ACCESS	read-only
	STATUS	mandatory
	DESCRIPTION
		"The number of frames successfully transmitted to the broadcast
		address. This counter does not include frames sent to a
		multicast address."
	::= { ieee8023IfEntry 8 }

ieee8023LateColls OBJECT-TYPE
	SYNTAX	Counter
	ACCESS	read-only
	STATUS	mandatory
	DESCRIPTION
		"The number of times that a collision has been detected later
		than 512 bit times into the transmission of a packet. 512 bit
		times is 51.2 micro secs. This type of collision is counted 
		twice - both as a late collision and as a regular, ordinary 
		collision."
	::= { ieee8023IfEntry 9 }

ieee8023ExcessColls OBJECT-TYPE
	SYNTAX	Counter
	ACCESS	read-only
	STATUS	mandatory
	DESCRIPTION
		"The number of frames that are not transmitted because of
		excessive collisions."
	::= { ieee8023IfEntry 10 }

ieee8023IntlMacTxError OBJECT-TYPE
	SYNTAX	Counter
	ACCESS	read-only
	STATUS	mandatory
	DESCRIPTION
		"The number of frames that would otherwise be transmitted by
		the station, but could not be sent because of an internal MAC
		sublayer transmit error. If this counter is incremented, then
		none of the other counters in this section are incremented.
		The exact meaning and mechanism for incrementing this counter
		is implementation dependent. In short, this is the count of 
		errors for which there are no specific counters."
	::= { ieee8023IfEntry 11 }

ieee8023CsErrors OBJECT-TYPE
	SYNTAX	Counter
	ACCESS	read-only
	STATUS	mandatory
	DESCRIPTION
		"The number of times that carrier sense was lost or never
		appeared when attempting to transmit a packet. This counter is
		incremented ONCE per transmission attempt, even if Carrier
		Sense fluctuates."
	::= { ieee8023IfEntry 12 }

ieee8023ExcessDef OBJECT-TYPE
	SYNTAX	Counter
	ACCESS	read-only
	STATUS	mandatory
	DESCRIPTION
		"The number of frames that deferred for an excessive period of
		time."
	::= { ieee8023IfEntry 13 }

ieee8023FrmsRxOk OBJECT-TYPE
	SYNTAX	Counter
	ACCESS	read-only
	STATUS	mandatory
	DESCRIPTION
		"The number of frames that are successfully received. This
		counter does not include frames received with frame-too-long,
		FCS, length, or alignment errors, or frames lost because of
		internal MAC sublayer error. This counter includes broadcast 
		and multicast frames that are received."
	::= { ieee8023IfEntry 14 }

ieee8023OctetsRxOk OBJECT-TYPE
	SYNTAX	Counter
	ACCESS	read-only
	STATUS	mandatory
	DESCRIPTION
		"The number entry of data and padding octets in frames that are
		successfully received. This counter does not include frames
		received with frame-too-long, FCS, length, or alignment
		errors, or frames lost because of internal MAC sublayer error.
		This counter includes octets in broadcast and multicast frames
		that are received. This counter does not include the octets 
		in the address,	length/type, and CRC fields."
	::= { ieee8023IfEntry 15 }

ieee8023McastFrmsRxOk OBJECT-TYPE
	SYNTAX	Counter
	ACCESS	read-only
	STATUS	mandatory
	DESCRIPTION
		"The number of frames that are successfully received and are
		directed to an active non-broadcast group address. This
		counter does not include frames received with frame-too-long,
		FCS, length, or alignment errors, or frames lost because of
		internal MAC sublayer error. Only frames for a multicast 
		address that this interface is receiving are counted. 
		Broadcast packets are not included."
	::= { ieee8023IfEntry 16 }

ieee8023BcastFrmsRxOk OBJECT-TYPE
	SYNTAX	Counter
	ACCESS	read-only
	STATUS	mandatory
	DESCRIPTION
		"The number of frames that are successfully received and are
		directed to the broadcast group address. This counter does not
		include frames received with frame-too-long, FCS, length, or
		alignment errors, or frames lost because of internal MAC
		sublayer error.	Multicast packets are not included."
	::= { ieee8023IfEntry 17 }

ieee8023TooLongErrors OBJECT-TYPE
	SYNTAX	Counter
	ACCESS	read-only
	STATUS	mandatory
	DESCRIPTION
		"The number of frames that are received and exceed the maximum
		permitted frame size. This counter is incremented when the
		frameTooLong error is returned."
	::= { ieee8023IfEntry 18 }

ieee8023AlignErrors OBJECT-TYPE
	SYNTAX	Counter
	ACCESS	read-only
	STATUS	mandatory
	DESCRIPTION
		"The number of frames that are not an integral number of octets
		in length and do not pass the FCS check. This counter is
		incremented when the alignmentError status is returned to the
		LLC."
	::= { ieee8023IfEntry 19 }

ieee8023FcsErrors OBJECT-TYPE
	SYNTAX	Counter
	ACCESS	read-only
	STATUS	mandatory
	DESCRIPTION
		"The number of frames that are an integral number of octets in
		length and do not pass the FCS check. This counter is
		incremented when the frameCheckError status is returned to the
		LLC."
	::= { ieee8023IfEntry 20 }

ieee8023IrLengthErrors OBJECT-TYPE
	SYNTAX	Counter
	ACCESS	read-only
	STATUS	mandatory
	DESCRIPTION
		"The number of frames with a length field value between the
		minimum unpadded LLC data size and the maximum allowed LLC
		data size inclusive, and which do not match the number of LLC
		data octets received. The counter also contains frames with a
		length field value less than the minimum unpadded LLC data
		size."
	::= { ieee8023IfEntry 21 }

ieee8023OorLengthFields OBJECT-TYPE
	SYNTAX	Counter
	ACCESS	read-only
	STATUS	mandatory
	DESCRIPTION
		"The number of frames with a length field value greater than
		the maximum allowed LLC data size. If true 802.3 is followed 
		for layer management, then this	counter will be incremented for
		every IP or ARP frame received that uses the Ethernet 
		encapsulation method. Both IP and ARP use type field values 
		that will cause this counter to be incremented, showing a 
		high error rate."
	::= { ieee8023IfEntry 22 }

ieee8023IntlMacRxErrors OBJECT-TYPE
	SYNTAX	Counter
	ACCESS	read-only
	STATUS	mandatory
	DESCRIPTION
		"The number of frames that would otherwise be received by the
		station, but could not be accepted because of an internal MAC
		sublayer receive error. If this counter is incremented, then
		none of the other counters in this section are incremented.
		The exact meaning and mechanism for incrementing this counter
		is implementation dependent. This is the count of other 
		errors."
	::= { ieee8023IfEntry 23 }

ieee8023InitMac OBJECT-TYPE
	SYNTAX	INTEGER {
		initialize(1),
		uninitialize(2)
		}
	ACCESS	read-write
	STATUS	mandatory
	DESCRIPTION
		"Reinitializes the MAC and PLS (physical layer signaling). All
		MIB counters are set to 0. The states of the status variables
		(described below) are as follows:
			- The receive and transmit Layer Management state 
			  variables (receiveEnabled and transmitEnabled) are 
			  set to enable reception and transmission of frames.
			- The promiscuous receive function is disabled.
			- Multicast reception is disabled."
	::= { ieee8023IfEntry 24 }

ieee8023PromRxStatus OBJECT-TYPE
	SYNTAX	INTEGER {
		enabled(1),
		disabled(2)
		}
	ACCESS	read-write
	STATUS	mandatory
	DESCRIPTION
		"This variable combines the enable ieee8023PromRx, disable
		ieee8023PromRx, and read ieee8023PromStatus MAC actions.
		Setting this variable to enabled causes the interface to
		accept frames regardless of their destination address.
		When enabled, all received frames increment all counters as
		though those frames were directed to this station.
		Frames can be promiscuously received only if the
		ieee8023MacSubLayerStatus variable is also set to enabled(1)."
	::= { ieee8023IfEntry 25 }

ieee8023MacSubLayerStatus OBJECT-TYPE
	SYNTAX	INTEGER {
		enabled(1),
		disabled(2)
		}
	ACCESS	read-write
	STATUS	mandatory
	DESCRIPTION
		"This variable causes the MAC sublayer to enter the normal
		operational state at idle. The PLS is reset by this operation.
		It is accomplished by setting receiveEnabled and
		transmitEnabled to true. Setting this variable to enabled(1) 
		enables the MAC sublayer to both receive and transmit frames. 
		Setting this variable to enabled(1) will also set the 
		ieee8023TransmitStatus variable to enabled(1). Similarly, 
		setting this variable to disabled(2) will also set 
		ieee8023TransmitStatus to disabled(2). Modifying this variable 
		does not change the state of any other variables. If the 
		variable is set to disabled(2), then any current 
		transmission/reception is completed before the 
		transmission/reception process is disabled. The value 
		returned when this variable is read is the logical and of the 
		receiveEnabled and transmitEnabled MAC internal	state 
		variables. If both are in the enabled state, then enabled(1) 
		is returned; otherwise disabled(2) is returned."
	::= { ieee8023IfEntry 26 }

ieee8023TxStatus OBJECT-TYPE
	SYNTAX	INTEGER {
		enabled(1),
		disabled(2)
		}
	ACCESS	read-write
	STATUS	mandatory
	DESCRIPTION
		"This variable enables the MAC sublayer to be explicitly
		enabled/disabled for transmitting frames. If a frame is being 
		transmitted when this variable is set to disabled(2), that 
		transmission is completed. Note that ieee8023MACSubLayerStatus
 		has an effect on this variable."
	::= { ieee8023IfEntry 27 }

ieee8023McastRxStatus OBJECT-TYPE
	SYNTAX	INTEGER {
		enabled(1),
		disabled(2)
		}
	ACCESS	read-write
	STATUS	mandatory
	DESCRIPTION
		"Enables/disables reception of multicast frames. To actually
		receive multicasts, both this variable AND
		ieee8023MacSubLayerStatus must be set to enabled."
	::= { ieee8023IfEntry 28 }

ieee8023MacAddress OBJECT-TYPE
	SYNTAX	PhysAddress (SIZE (6))
	ACCESS	read-write
	STATUS	mandatory
	DESCRIPTION
		"This object contains the MAC station address (i.e., the
		Ethernet address)."
	::= { ieee8023IfEntry 29 }

ieee8023SqeTestErrors OBJECT-TYPE
	SYNTAX	Counter
	ACCESS	read-only
	STATUS	mandatory
	DESCRIPTION
		"The number of times that the SQE TEST ERROR status was
		received."
	::= { ieee8023IfEntry 30 }


-- SECTION 3: Collision Frames Table

ieee8023CollTable OBJECT-TYPE
	SYNTAX	SEQUENCE OF Ieee8023CollEntry
	ACCESS	not-accessible
	STATUS	mandatory
	DESCRIPTION
		"A table containing information on collision activity."
	::= { ieee8023 2 }

ieee8023CollEntry OBJECT-TYPE
	SYNTAX	Ieee8023CollEntry
	ACCESS	not-accessible
	STATUS	mandatory
	INDEX	{ ieee8023CollRetrans, ieee8023CollIndex }
	::= { ieee8023CollTable 1 }

Ieee8023CollEntry ::= SEQUENCE {
	ieee8023CollRetrans
		INTEGER,
	ieee8023CollIndex
		INTEGER,
	ieee8023Collisions
		Counter
	}

ieee8023CollRetrans OBJECT-TYPE
	SYNTAX	INTEGER
	ACCESS	read-only
	STATUS	mandatory
	DESCRIPTION
		"The entry corresponding to the number of attempts made before
		a frame was successfully transmitted. The range is from 1 to
		15."
	::= { ieee8023CollEntry 1 }

ieee8023CollIndex OBJECT-TYPE
	SYNTAX	INTEGER
	ACCESS	read-only
	STATUS	mandatory
	DESCRIPTION
		"The index value that uniquely identifies the interface to
		which this entry is applicable. The interface identified by a
		particular value of this index is the same interface as
		identified by the same value of ifIndex."
	::= { ieee8023CollEntry 2 }

ieee8023Collisions OBJECT-TYPE
	SYNTAX	Counter
	ACCESS	read-only
	STATUS	mandatory
	DESCRIPTION
		"The number of frames that were retransmitted a specific number
		of times."
	::= { ieee8023CollEntry 3 }


-- SECTION 4: Multicast Address Table

ieee8023GroupTable OBJECT-TYPE
	SYNTAX	SEQUENCE OF Ieee8023GroupEntry
	ACCESS	not-accessible
	STATUS	mandatory
	DESCRIPTION
		"A table containing information on group addresses. There are
		five entries in the table."
	::= { ieee8023 3 }

ieee8023GroupEntry OBJECT-TYPE
	SYNTAX	Ieee8023GroupEntry
	ACCESS	not-accessible
	STATUS	mandatory
	INDEX	{ ieee8023GroupIndex, ieee8023GroupAddress }
	::= { ieee8023GroupTable 1 }

Ieee8023GroupEntry ::= SEQUENCE {
	ieee8023GroupIndex
		INTEGER,
	ieee8023GroupAddress
		PhysAddress,
	ieee8023GroupType
		INTEGER
	}

ieee8023GroupIndex OBJECT-TYPE
	SYNTAX	INTEGER
	ACCESS	read-only
	STATUS	mandatory
	DESCRIPTION
		"The index value that uniquely identifies the interface to
		which this entry is applicable. The interface identified by a
		particular value of this index is the same interface as
		identified by the same value of ifIndex."
	::= { ieee8023GroupEntry 1 }

ieee8023GroupAddress OBJECT-TYPE
	SYNTAX	PhysAddress (SIZE (6))
	ACCESS	read-only
	STATUS	mandatory
	DESCRIPTION
		"A group address to which this Ethernet-like interface
		responds."
	::= { ieee8023GroupEntry 2 }

ieee8023GroupType OBJECT-TYPE
	SYNTAX	INTEGER {
		other(1),		-- none of the following
		invalid(2)		-- an invalidated group
		}
	ACCESS	read-write
	STATUS	mandatory
	DESCRIPTION
		"Type of group address.	Setting this object to the value 
		invalid(2) invalidates the corresponding entry in the 
		ieee8023GroupTable. That is, it	effectively disassociates the 
		interface identified with said entry from the group address 
		identified with said entry. Whether the agent removes an 
		invalidated entry from the table is an implementation-specific
 		matter. Accordingly, management	stations must be prepared to 
		receive tabular information from agents that corresponds to 
		entries not currently in use. Proper interpretation of such 
		entries requires examination of	the relevant ieee8023GroupType
 		object."
	::= { ieee8023GroupEntry 3 }

END


-- file:  tr3.1-10.25.91

SYNOPTICS-TOKENRING-MIB

-- Token Ring MIB 3.1
-- DRAFT Revision 10/25/91
-- Printed 10/29/91

-- Copyright 1991 SynOptics Communications, Inc.  All Rights
-- Reserved.  Reproduction of this document is authorized on
-- condition that the foregoing copyright notice is included.
-- This SynOptics SNMP Management Information Base Specification
-- (Specification) embodies SynOptics' confidential and
-- proprietary intellectual property.  SynOptics retains all
-- title and ownership in the Specification, including any
-- revisions.  
--
-- It is SynOptics intent to encourage the widespread use of
-- this Specification in connection with the management of
-- SynOptics products. SynOptics grants vendors, end-users,
-- and other interested parties a non-exclusive license to
-- use this Specification in connection with the management
-- of SynOptics products.
--
-- This Specification is supplied "AS IS," and SynOptics makes
-- no warranty, either express or implied, as to the use,
-- operation, condition, or performance of the Specification.


DEFINITIONS ::= BEGIN


-- SECTION 1: Top Level Definitions

-- Imports

IMPORTS
	Counter, TimeTicks	FROM RFC1155-SMI
	OBJECT-TYPE		FROM RFC-1212
	s3000TokenRing		FROM SYNOPTICS-COMMON-MIB;


-- Groups

s3000TrBoard		OBJECT IDENTIFIER ::= { s3000TokenRing 2 }
s3000TrPort		OBJECT IDENTIFIER ::= { s3000TokenRing 3 }
s3000TrNmm		OBJECT IDENTIFIER ::= { s3000TokenRing 4 }
s3000TrNode		OBJECT IDENTIFIER ::= { s3000TokenRing 5 }
s3000TrRing		OBJECT IDENTIFIER ::= { s3000TokenRing 7 }
s3TrRingStats		OBJECT IDENTIFIER ::= { s3000TrRing 1 }


-- SECTION 2: Token Ring Board Group


-- Common Board Table

s3TrCommonBoardTable OBJECT-TYPE
	SYNTAX	SEQUENCE OF S3TrCommonBoardEntry
	ACCESS	not-accessible
	STATUS	mandatory
	DESCRIPTION
		"Information maintained for each token ring board.  The 
		information can be retrieved for any token ring board, even if
 		the board is not on the same backplane ring as this NMM. The 
		instance is the slot number of the concentrator that the board 
		occupies."
	::= { s3000TrBoard 2 }

s3TrCommonBoardEntry OBJECT-TYPE
	SYNTAX	S3TrCommonBoardEntry
	ACCESS	not-accessible
	STATUS	mandatory
	DESCRIPTION
		"There is one entry per board in this table."
	INDEX	{ s3TrCommonBoardIndex }
	::= { s3TrCommonBoardTable 1 }

S3TrCommonBoardEntry ::= SEQUENCE {
	s3TrCommonBoardIndex
		INTEGER,
	s3TrCommonBoardRing1or2
		INTEGER,
	s3TrCommonBoardRingSpeed
		INTEGER
}
		
s3TrCommonBoardIndex OBJECT-TYPE
	SYNTAX	INTEGER
	ACCESS	read-only
	STATUS	mandatory
	DESCRIPTION
		"A unique value for each board.  Its value ranges between 1 
		and 12. The value for each board must remain constant at 
		least from one re-initialization of the entity's network 
		management system to the next re-initialization. If a board is
 		inserted or reinserted in a concentrator then the NMM has to 
		be reinitialized."
	::= { s3TrCommonBoardEntry 1 }

s3TrCommonBoardRing1or2 OBJECT-TYPE
	SYNTAX	INTEGER {
		other(1),	-- not a valid ring number
		ring1(2),	-- use/using ring 1 on the concentrator
		ring2(3)	-- use/using ring 2 on the concentrator
	}	
	ACCESS	read-only
	STATUS	mandatory
	DESCRIPTION
		"Determines which ring the board is currently using on the 
		concentrator backplane."
	::=  { s3TrCommonBoardEntry 2 }

s3TrCommonBoardRingSpeed OBJECT-TYPE
	SYNTAX	INTEGER {
		other(1),	-- unknown speed
		speed1M(2),	-- 1 Mbps for standard compatibility
		speed4M(3),	-- 4 Mbps
		speed16M(4)	-- 16 Mbps
	}	
	ACCESS	read-only
	STATUS	mandatory
	DESCRIPTION
		"Token Ring speed of the ring that this board is connected to."
	::=  { s3TrCommonBoardEntry 3 }



-- SECTION 3: Token Ring Port Group


-- Port Table

s3TrPortTable OBJECT-TYPE
	SYNTAX	SEQUENCE OF S3TrPortEntry
	ACCESS	not-accessible
	STATUS	mandatory
	DESCRIPTION
		"A table containing information about each port of a LattisNet 
		concentrator.  The number of entries is given by knowing the 
		number of occupied slots in s3ChassisSlotConfigTable whose 
		s3SlotModuleType is of a token ring type and is on the same 
		physical ring as the agent NMM."
	::= { s3000TrPort 1 }

s3TrPortEntry OBJECT-TYPE
	SYNTAX	S3TrPortEntry
	ACCESS	not-accessible
	STATUS	mandatory
	DESCRIPTION
		"A port entry containing objects at the port level for a 
		particular port."
	INDEX	{ s3TrPortBoardIndex, s3TrPortIndex }
	::= { s3TrPortTable 1 }

S3TrPortEntry ::= SEQUENCE {
	s3TrPortBoardIndex
		INTEGER,
	s3TrPortIndex
		INTEGER,
	s3TrPortWrap
		INTEGER,
	s3TrPortTestLatch
		INTEGER,
	s3TrPortRelayStatus
		INTEGER,
	s3TrPortPhantomStatus
		INTEGER,
	s3TrPortPhantomChangeFlag
		INTEGER,
	s3TrPortChgSyn2IBM
		INTEGER,
	s3TrPortStrap
		INTEGER
}

s3TrPortBoardIndex OBJECT-TYPE
	SYNTAX	INTEGER
	ACCESS	read-only
	STATUS	mandatory
	DESCRIPTION
		"A unique value for each board.  Its value ranges between 1 
		and 12. The value for each board must remain constant at 
		least from one re-initialization of the entity's network 
		management system to the next re-initialization. If a board 
		is inserted or reinserted in a concentrator then the NMM has 
		to be reinitialized."
	::=  { s3TrPortEntry 1 }

s3TrPortIndex OBJECT-TYPE
	SYNTAX	INTEGER
	ACCESS	read-only
	STATUS	mandatory
	DESCRIPTION
		"A unique value for each port.  Its value ranges between 1 
		and 12. The value for each port must remain constant at least 
		from one re-initialization of the entity's network management 
		system to the next re-initialization.  If the board is an NMM 
		board it will only have 2 ports, with Port 1 being for Ring In
		and Port 2 being for Ring Out."
	::=  { s3TrPortEntry 2 }

s3TrPortWrap OBJECT-TYPE
	SYNTAX	INTEGER {
		other(1),	-- port not wrapped or connected
		wrap(2),
		connect(3)
	}
	ACCESS	read-write
	STATUS	mandatory
	DESCRIPTION
		"Status of the port.  Setting wrap(2) disconnects the port 
		from the ring and setting this object to connect(3) connects 
		the port to the ring."
	::=  { s3TrPortEntry 3 }

s3TrPortTestLatch OBJECT-TYPE
	SYNTAX	INTEGER {
		other(1),	-- not supported
		on(2),		-- test latch activated
		off(3)		-- test latch not activated
	}
	ACCESS	read-write
	STATUS	mandatory
	DESCRIPTION
		"Status of the test latch which is used to set the channel 
		decoder used to monitor the health of the communication path 
		between the NMM and the module channel."
	::=  { s3TrPortEntry 4 }

s3TrPortRelayStatus OBJECT-TYPE
	SYNTAX	INTEGER {
		other(1),	-- not supported
		on(2),		-- channel is part of the ring
		off(3)		-- channel is bypassed
	}
	ACCESS	read-only
	STATUS	mandatory
	DESCRIPTION
		"Status of the channel's present relay mode.  On(2) means the 
		channel is in the ring and off(3) means the channel is 
		bypassed."
	::=  { s3TrPortEntry 5 }

s3TrPortPhantomStatus OBJECT-TYPE
	SYNTAX	INTEGER {
		other(1),
		on(2),
		off(3)
	}
	ACCESS	read-only
	STATUS	mandatory
	DESCRIPTION
		"Status of the ring access request signal."
	::=  { s3TrPortEntry 6 }

s3TrPortPhantomChangeFlag OBJECT-TYPE
	SYNTAX	INTEGER {
		other(1),
		noChange(2),
		change(3)
	}
	ACCESS	read-only
	STATUS	mandatory
	DESCRIPTION
		"Change(3) indicates that port phantom has been changed from 
		OFF to ON.  After inquiry by NMS, it will be cleared to 
		noChange(2).  Port phantom changing from ON to OFF has no 
		impact on this object."
	::=  { s3TrPortEntry 7 }

s3TrPortChgSyn2IBM OBJECT-TYPE
	SYNTAX	INTEGER {
		notSupported(1),
		synoptics(2),
		ibm(3)
	}
	ACCESS	read-write
	STATUS	mandatory
	DESCRIPTION
		"If the port is on a ring in/ring out module this object 
		changes the strap state depending on the jumper setting 
		retrieved as s3TrPortStrap.  If the strap is set for SynOptics
 		phantom option, this object can be changed to ibm(3).  If the 
		strap is set for non-SynOptics option, this object can not be 
		changed. Non ring in/ring out modules or fiber ring in/ring out
		modules must take on the value of notSupported(1)."
	::=  { s3TrPortEntry 8 }

s3TrPortStrap OBJECT-TYPE
	SYNTAX	INTEGER {
		notSupported(1),
		synoptics(2),
		ibm(3)
	}
	ACCESS	read-only
	STATUS	mandatory
	DESCRIPTION
		"If the port is on a ring in/ring out module this object 
		signifies whether the hardware jumper is in synoptics(2) mode 
		or ibm(3) mode.  This information is retrieved using a  NMI 
		command. For ports on fiber ring in/ring out modules, and 
		those ports not on ring in/ring out modules, the agent always 
		returns notSupported(1)."
	::=  { s3TrPortEntry 9 }


-- SECTION 4: Token Ring NMM Group


s3TrNmmFnNum OBJECT-TYPE
	SYNTAX	INTEGER
	ACCESS	read-write
	STATUS	mandatory
	DESCRIPTION
		"Defines the flat network number that this NMM is part of."
	::=  { s3000TrNmm 1 }

s3TrNmmRingNum OBJECT-TYPE
	SYNTAX	INTEGER
	ACCESS	read-only
	STATUS	mandatory
	DESCRIPTION
		"Defines the segment number that this NMM is connected to."
	::=  { s3000TrNmm 2 }

s3TrNmmSlotNum OBJECT-TYPE
	SYNTAX	INTEGER
	ACCESS	read-only
	STATUS	deprecated
	DESCRIPTION
		"Defines the slot number that this NMM is connected to.  New 
		NMS implementations should use the object s3AgentMySlotId 
		defined in the common MIB."
	::=  { s3000TrNmm 3 }

s3TrNmmFpuIdRev OBJECT-TYPE
	SYNTAX	INTEGER
	ACCESS	read-only
	STATUS	mandatory
	DESCRIPTION
		"The revision of the Front-end Frame Processing unit.  
		0=Rev. A, 1=Rev. B, etc."
	::=  { s3000TrNmm 4 }

s3TrNmmFpuStatus OBJECT-TYPE
	SYNTAX	INTEGER {
		notPresent(1),
		notOperational(2),	-- present, but not operational
		operational(3)		-- present and operational
	}
	ACCESS	read-only
	STATUS	mandatory
	DESCRIPTION
		"The status of the Front-end Frame Processing Unit."
	::=  { s3000TrNmm 5 }

s3TrNmmDramSize OBJECT-TYPE
	SYNTAX	INTEGER{
		other(1),	-- unknown size
		k512(2),	-- 512K memory
		oneMeg(3),
		twoMeg(4)
	}
	ACCESS	read-only
	STATUS	mandatory
	DESCRIPTION
		"The highest address of the DRAM in the NMM memory map."
	::=  { s3000TrNmm 6 }

s3TrNmmEepromSize OBJECT-TYPE
	SYNTAX	INTEGER {
		other(1),	-- unknown size
		k2kby8(2),	-- 2k*8
		k8kby8(3)	-- 8k*8
	}
	ACCESS	read-only
	STATUS	mandatory
	DESCRIPTION
		"The size of the EEPROM in the NMM memory map."
	::=  { s3000TrNmm 7 }

s3TrNmmGrpAddrFrmsRxOk OBJECT-TYPE
	SYNTAX	Counter	
	ACCESS	read-only
	STATUS	mandatory
	DESCRIPTION
		"Number of Group Address frames received without error by this 
		NMM. Note:  The NMM counts only Group Address frames that are 
		addressed to its own Group Address(es)."
	::=  { s3000TrNmm 8 }

s3TrNmmRing1or2 OBJECT-TYPE
	SYNTAX	INTEGER {
		other(1),	-- not a valid ring number
		ring1(2),	-- use/using ring 1 on the concentrator
		ring2(3)	-- use/using ring 2 on the concentrator
	}	
	ACCESS	read-only
	STATUS	mandatory
	DESCRIPTION
		"Determines which ring the NMM is currently using on the 
		concentrator backplane."
	::=  { s3000TrNmm 9 }

s3TrNmmRingSpeed OBJECT-TYPE
	SYNTAX	INTEGER {
		other(1),	-- unknown speed
		speed1M(2),	-- 1 Mbps for standard compatibility
		speed4M(3),	-- 4 Mbps
		speed16M(4)	-- 16 Mbps
	}	
	ACCESS	read-only
	STATUS	mandatory
	DESCRIPTION
		"Token Ring speed."
	::=  { s3000TrNmm 10 }

s3TrNmmHexDisplay OBJECT-TYPE
	SYNTAX	OCTET STRING (SIZE(4))	
	ACCESS	read-only
	STATUS	mandatory
	DESCRIPTION
		"4 octet hex display string that is displayed on the NMM 
		control panel."
	::=  { s3000TrNmm 11 }

s3TrNmmEpromSize OBJECT-TYPE
	SYNTAX	INTEGER {
		other(1),		-- unknown size
		k2kby8(2),		-- 2k*8
		k8kby8(3),		-- 8k*8
		k16kby8(4),		-- 16k*8
		k32kby8(5),		-- 32k*8
		k64kby8(6),		-- 64k*8
		k128kby8(7),		-- 128k*8
		k256kby8(8)		-- 256k*8
	}
	ACCESS	read-only
	STATUS	mandatory
	DESCRIPTION
		"The size of the EPROM in the NMM memory map."
	::=  { s3000TrNmm 12 }



-- SECTION 5: Token Ring Station Group


-- Node table

-- list of all nodes that are active on the local token ring that this 
-- concentrator is connected to.

s3TrNodeTable OBJECT-TYPE
	SYNTAX	SEQUENCE OF S3TrNodeEntry
	ACCESS	not-accessible
	STATUS	mandatory
	DESCRIPTION
		"Table containing station specific information."
	::= { s3000TrNode 1 }

s3TrNodeEntry OBJECT-TYPE
	SYNTAX	S3TrNodeEntry
	ACCESS	not-accessible
	STATUS	mandatory
	DESCRIPTION
		"Entry in the table containing counters and profiling 
		information for each node detected on the local token ring."
	INDEX	{ s3TrNodeEntMacAddress }
	::= { s3TrNodeTable 1 }

S3TrNodeEntry ::= SEQUENCE {
	s3TrNodeEntMacAddress
		OCTET STRING,
	s3TrNodeEntStatus
		INTEGER,
	s3TrNodeEntNodeStatus
		OCTET STRING,
	s3TrNodeLineErrs
		Counter,
	s3TrNodeBurstErrs
		Counter,
	s3TrNodeAriFciErrs
		Counter,
	s3TrNodeLostFrames
		Counter,
	s3TrNodeRcvCongestErrs
		Counter,
	s3TrNodeFrmCopyErrs
		Counter,
	s3TrNodeTokenErrs
		Counter,
	s3TrNodeInternalErrs
		Counter,
	s3TrNodeAbortTransErrs
		Counter,
	s3TrNodeFrequencyErrs
		Counter,
	s3TrNodeEntProductId
		OCTET STRING,
	s3TrNodeEntUna
		OCTET STRING,
	s3TrNodeEntNodeVersion
		OCTET STRING,
	s3TrNodeEntPhysDrop
		OCTET STRING,
	s3TrNodeEntFuncAddr
		OCTET STRING,
	s3TrNodeEntAuthFuncClass
		OCTET STRING,
	s3TrNodeEntAuthAccPriority
		OCTET STRING,
	s3TrNodeEntGrpAddr
		OCTET STRING,
	s3TrNodeEntStationId
		OCTET STRING,
	s3TrNodeEntBeaconType
		INTEGER,
	s3TrNodeBeaconCnt
		Counter,
	s3TrNodeLastBeaconTime
		TimeTicks,
	s3TrNodeLastInsertTime
		TimeTicks,
	s3TrNodeFirstInsertTime
		TimeTicks,
	s3TrNodeLastDeinsertTime
		TimeTicks,
	s3TrNodeRemoveStation
		INTEGER
}

s3TrNodeEntMacAddress OBJECT-TYPE
	SYNTAX	OCTET STRING (SIZE(6))
	ACCESS	read-only
	STATUS	mandatory
	DESCRIPTION
		"MAC address of node that this entry in the table is for."
	::=  { s3TrNodeEntry 1 }

s3TrNodeEntStatus OBJECT-TYPE
	SYNTAX	INTEGER {
		beaconing(1),
		notBeaconing(2)
	}
	ACCESS	read-only
	STATUS	mandatory
	DESCRIPTION
		"Tells whether the station is currently beaconing or not."
	::=  { s3TrNodeEntry 4 }

s3TrNodeEntNodeStatus OBJECT-TYPE
	SYNTAX	OCTET STRING (SIZE(6))
	ACCESS	read-only
	STATUS	mandatory
	DESCRIPTION
		"Node status as defined in 802.5 specification 
		(section 3.3.2.18)."
	::=  { s3TrNodeEntry 5 }

s3TrNodeLineErrs OBJECT-TYPE
	SYNTAX	Counter
	ACCESS	read-only
	STATUS	mandatory
	DESCRIPTION
		"Number of line errors.  Section 3.8.1 of IEEE 802.5 
		specification."
	::=  { s3TrNodeEntry 6 }

s3TrNodeBurstErrs OBJECT-TYPE
	SYNTAX	Counter
	ACCESS	read-only
	STATUS	mandatory
	DESCRIPTION
		"Number of burst errors.  Section 3.8.3 of IEEE 802.5 
		specification."
	::=  { s3TrNodeEntry 7 }

s3TrNodeAriFciErrs OBJECT-TYPE
	SYNTAX	Counter
	ACCESS	read-only
	STATUS	mandatory
	DESCRIPTION
		"Number of ARI FCI errors.  See AC errors, Section 3.8.4 of 
		IEEE 802.5 specification."
	::=  { s3TrNodeEntry 8 }

s3TrNodeLostFrames OBJECT-TYPE
	SYNTAX	Counter
	ACCESS	read-only
	STATUS	mandatory
	DESCRIPTION
		"Number of frames lost.  Section 3.8.6 of IEEE 802.5 
		specification."
	::=  { s3TrNodeEntry 9 }

s3TrNodeRcvCongestErrs OBJECT-TYPE
	SYNTAX	Counter
	ACCESS	read-only
	STATUS	mandatory
	DESCRIPTION
		"Number of receive congestion errors.  Section 3.8.7 of IEEE 
		802.5 specification."
	::=  { s3TrNodeEntry 10 }

s3TrNodeFrmCopyErrs OBJECT-TYPE
	SYNTAX	Counter
	ACCESS	read-only
	STATUS	mandatory
	DESCRIPTION
		"Number of frame copy errors.  Section 3.8.8 of IEEE 802.5 
		specification."
	::=  { s3TrNodeEntry 11 }

s3TrNodeTokenErrs OBJECT-TYPE
	SYNTAX	Counter
	ACCESS	read-only
	STATUS	mandatory
	DESCRIPTION
		"Number of token errors.  Section 3.8.10 of IEEE 802.5 specification."
	::=  { s3TrNodeEntry 12 }

s3TrNodeInternalErrs OBJECT-TYPE
	SYNTAX	Counter
	ACCESS	read-only
	STATUS	mandatory
	DESCRIPTION
		"Number of internal errors.  Section 3.8.2 of IEEE 802.5 
		specification."
	::=  { s3TrNodeEntry 13 }

s3TrNodeAbortTransErrs OBJECT-TYPE
	SYNTAX	Counter
	ACCESS	read-only
	STATUS	mandatory
	DESCRIPTION
		"Number of abort delimiter transmitted errors.  Section 3.8.5 
		of IEEE 802.5 specification."
	::=  { s3TrNodeEntry 14 }

s3TrNodeFrequencyErrs OBJECT-TYPE
	SYNTAX	Counter
	ACCESS	read-only
	STATUS	mandatory
	DESCRIPTION
		"Number of frequency errors. Section 3.8.9 of IEEE 802.5 
		specification."
	::=  { s3TrNodeEntry 15 }

s3TrNodeEntProductId OBJECT-TYPE
	SYNTAX	OCTET STRING (SIZE(18))
	ACCESS	read-only
	STATUS	mandatory
	DESCRIPTION
		"A brief string describing the product specified by the vendor.
		Section 3.3.2.14 of IEEE 802.5 specification. The characters 
		in the string are represented in EBCDIC for IBM products, in 
		ASCII for others."
	::=  { s3TrNodeEntry 16 }

s3TrNodeEntUna OBJECT-TYPE
	SYNTAX	OCTET STRING (SIZE(6))
	ACCESS	read-only
	STATUS	mandatory
	DESCRIPTION
		"The Upstream Neighbor Address.  Section 3.3.2.15 of IEEE 
		802.5 specification."
	::=  { s3TrNodeEntry 17 }

s3TrNodeEntNodeVersion OBJECT-TYPE
	SYNTAX	OCTET STRING (SIZE(10))
	ACCESS	read-only
	STATUS	mandatory
	DESCRIPTION
		"String that represents the version of the station software.  
		Section 3.3.2.17 of IEEE 802.5 specification. The characters 
		in the string are represented in EBCDIC for IBM products, in 
		ASCII for others."
	::=  { s3TrNodeEntry 18 }

s3TrNodeEntPhysDrop OBJECT-TYPE
	SYNTAX	OCTET STRING (SIZE(4))
	ACCESS	read-only
	STATUS	mandatory
	DESCRIPTION
		"This reports the physical location of this node on the ring.  
		Section 3.3.2.13 of IEEE 802.5 specification."
	::=  { s3TrNodeEntry 19 }

s3TrNodeEntFuncAddr OBJECT-TYPE
	SYNTAX	OCTET STRING (SIZE(6))
	ACCESS	read-only
	STATUS	mandatory
	DESCRIPTION
		"Specifies the functional addresses used by this station.  
		Section 3.3.2.8 of IEEE 802.5 specification."
	::=  { s3TrNodeEntry 20 }

s3TrNodeEntAuthFuncClass OBJECT-TYPE
	SYNTAX	OCTET STRING (SIZE(2))
	ACCESS	read-only
	STATUS	mandatory
	DESCRIPTION
		"This specifies the functional classes that are allowed to be 
		active in the station.  Section 3.3.2.3 of IEEE 802.5 
		specification."
	::=  { s3TrNodeEntry 21 }

s3TrNodeEntAuthAccPriority OBJECT-TYPE
	SYNTAX	OCTET STRING (SIZE(2))
	ACCESS	read-only
	STATUS	mandatory
	DESCRIPTION
		"The maximum priority this station is allowed to use.  Section 
		3.3.2.2 of IEEE 802.5 specification."
	::=  { s3TrNodeEntry 22 }

s3TrNodeEntGrpAddr OBJECT-TYPE
	SYNTAX	OCTET STRING (SIZE(6))
	ACCESS	read-only
	STATUS	mandatory
	DESCRIPTION
		"This contains the group address of this station.  Section 
		3.3.2.9 of IEEE 802.5 specification."
	::=  { s3TrNodeEntry 23 }

s3TrNodeEntStationId OBJECT-TYPE
	SYNTAX	OCTET STRING (SIZE(6))
	ACCESS	read-only
	STATUS	mandatory
	DESCRIPTION
		"This string is used to uniquely identify the station.  It may 
		be equal to the station's MAC address.  Section 3.3.2.21 of 
		IEEE 802.5 specification."
	::=  { s3TrNodeEntry 24 }

s3TrNodeEntBeaconType OBJECT-TYPE
	SYNTAX	INTEGER {
		reconfiguration(1),
		signal-loss(2),
		bit-streaming(3),
		contention-streaming(4)
	}
	ACCESS	read-only
	STATUS	mandatory
	DESCRIPTION
		"This specifies the type of beacon frame seen.  Section 
		3.3.2.4 of IEEE 802.5 specification." 
	::=  { s3TrNodeEntry 25 }

s3TrNodeBeaconCnt OBJECT-TYPE
	SYNTAX	Counter
	ACCESS	read-only
	STATUS	mandatory
	DESCRIPTION
		"Number of beacon frames that have been sent by this station."
	::=  { s3TrNodeEntry 26 }

s3TrNodeLastBeaconTime OBJECT-TYPE
	SYNTAX	TimeTicks
	ACCESS	read-only
	STATUS	mandatory
	DESCRIPTION
		"The time of the last beacon frame sent by this station."
	::=  { s3TrNodeEntry 27 }

s3TrNodeLastInsertTime OBJECT-TYPE
	SYNTAX	TimeTicks
	ACCESS	read-only
	STATUS	mandatory
	DESCRIPTION
		"The time of the last ring insertion by this station.  Time is 
		relative from the system uptime."
	::=  { s3TrNodeEntry 28 }

s3TrNodeFirstInsertTime OBJECT-TYPE
	SYNTAX	TimeTicks
	ACCESS	read-only
	STATUS	mandatory
	DESCRIPTION
		"The time of the first ring insertion by this station.  Time 
		is relative from the system uptime."
	::=  { s3TrNodeEntry 29 }

s3TrNodeLastDeinsertTime OBJECT-TYPE
	SYNTAX	TimeTicks
	ACCESS	read-only
	STATUS	mandatory
	DESCRIPTION
		"The time of the last ring deinsertion by this station.  Time 
		is relative from the system uptime."
	::=  { s3TrNodeEntry 30 }

s3TrNodeRemoveStation OBJECT-TYPE
	SYNTAX	INTEGER {
		other(1),	-- do nothing
		remove(2)	-- remove the MAC address 
	}
	ACCESS	read-write
	STATUS	mandatory
	DESCRIPTION
		"Removes the MAC address associated with this entry from the 
		ring by sending a REMOVE MAC frame if this object is written 
		to with remove(2)."
	::=  { s3TrNodeEntry 31 }



-- SECTION 6: Token Ring "RING" Group


s3TrRingStatus OBJECT-TYPE
	SYNTAX	INTEGER {
		beaconing(1),
		notbeaconing(2)
	}
	ACCESS	read-only
	STATUS	mandatory
	DESCRIPTION
		"The status of the ring."
	::=  { s3TrRingStats 1 }

s3TrRingFrmsRxOk OBJECT-TYPE
	SYNTAX	Counter
	ACCESS	read-only
	STATUS	mandatory
	DESCRIPTION
		"Number of frames received successfully by the NMM."
	::=  { s3TrRingStats 2 }

s3TrRingOctetsRxOk OBJECT-TYPE
	SYNTAX	Counter
	ACCESS	read-only
	STATUS	mandatory
	DESCRIPTION
		"Number of octets received successfully by the NMM."
	::=  { s3TrRingStats 3 }

s3TrRingBcastFrmsRxOk OBJECT-TYPE
	SYNTAX	Counter
	ACCESS	read-only
	STATUS	mandatory
	DESCRIPTION
		"Number of broadcast frames received successfully by the NMM."
	::=  { s3TrRingStats 4 }

s3TrRingLineErrs OBJECT-TYPE
	SYNTAX	Counter
	ACCESS	read-only
	STATUS	mandatory
	DESCRIPTION
		"Number of line errors.  Section 3.8.1 of IEEE 802.5 
		specification."
	::=  { s3TrRingStats 5 }

s3TrRingBurstErrs OBJECT-TYPE
	SYNTAX	Counter
	ACCESS	read-only
	STATUS	mandatory
	DESCRIPTION
		"Number of burst errors.  Section 3.8.3 of IEEE 802.5 specification."
	::=  { s3TrRingStats 6 }

s3TrRingAriFciErrs OBJECT-TYPE
	SYNTAX	Counter
	ACCESS	read-only
	STATUS	mandatory
	DESCRIPTION
		"Number of ARI FCI errors.  See AC errors, Section 3.8.4 of 
		IEEE 802.5 specification."
	::=  { s3TrRingStats 7 }

s3TrRingLostFrames OBJECT-TYPE
	SYNTAX	Counter
	ACCESS	read-only
	STATUS	mandatory
	DESCRIPTION
		"Number of frames lost.  Section 3.8.6 of IEEE 802.5 
		specification."
	::=  { s3TrRingStats 8 }

s3TrRingRcvCongestErrs OBJECT-TYPE
	SYNTAX	Counter
	ACCESS	read-only
	STATUS	mandatory
	DESCRIPTION
		"Number of receive congestion errors.  Section 3.8.7 of IEEE 
		802.5 specification."
	::=  { s3TrRingStats 9 }

s3TrRingFrmCopyErrs OBJECT-TYPE
	SYNTAX	Counter
	ACCESS	read-only
	STATUS	mandatory
	DESCRIPTION
		"Number of frame copy errors.  Section 3.8.8 of IEEE 802.5 
		specification."
	::=  { s3TrRingStats 10 }

s3TrRingTokenErrs OBJECT-TYPE
	SYNTAX	Counter
	ACCESS	read-only
	STATUS	mandatory
	DESCRIPTION
		"Number of token errors.  Section 3.8.10 of IEEE 802.5 
		specification."
	::=  { s3TrRingStats 11 }

s3TrRingInternalErrs OBJECT-TYPE
	SYNTAX	Counter
	ACCESS	read-only
	STATUS	mandatory
	DESCRIPTION
		"Number of internal errors.  Section 3.8.2 of IEEE 802.5 
		specification."
	::=  { s3TrRingStats 12 }

s3TrRingAbortTransErrs OBJECT-TYPE
	SYNTAX	Counter
	ACCESS	read-only
	STATUS	mandatory
	DESCRIPTION
		"Number of abort delimiter transmitted errors.  Section 3.8.5 
		of IEEE 802.5 specification."
	::=  { s3TrRingStats 13 }

s3TrRingFrequencyErrs OBJECT-TYPE
	SYNTAX	Counter
	ACCESS	read-only
	STATUS	mandatory
	DESCRIPTION
		"Number of frequency errors.  Section 3.8.9 of IEEE 802.5 
		specification."
	::=  { s3TrRingStats 14 }

s3TrRingBeaconCnt OBJECT-TYPE
	SYNTAX	Counter
	ACCESS	read-only
	STATUS	mandatory
	DESCRIPTION
		"Number of beacon frames that have been seen."
	::=  { s3TrRingStats 15 }

s3TrRingBeaconType OBJECT-TYPE
	SYNTAX	INTEGER {
		reconfiguration(1),
		signal-loss(2),
		bit-streaming(3),
		contention-streaming(4)
	}
	ACCESS	read-only
	STATUS	mandatory
	DESCRIPTION
		"This specifies the type of beacon frame seen.  Section 
		3.3.2.4 of IEEE 802.5 Specification."
	::=  { s3TrRingStats 16 }

s3TrRingLastBeaconTime OBJECT-TYPE
	SYNTAX	TimeTicks
	ACCESS	read-only
	STATUS	mandatory
	DESCRIPTION
		"The time of the last beacon frame sent on the ring.  Time is 
		relative from the system uptime."
	::=  { s3TrRingStats 17 }

s3TrRingBeaconStation OBJECT-TYPE
	SYNTAX	OCTET STRING (SIZE(6))
	ACCESS	read-only
	STATUS	mandatory
	DESCRIPTION
		"The MAC address of station last beaconing."
	::=  { s3TrRingStats 18 }


END


-- file:  traps1.0-09.30.91

SYNOPTICS-TRAP-MIB

-- Trap MIB Release 1.0
-- Revision 9/30/91
-- Printed 9/30/91

-- Copyright 1991 SynOptics Communications, Inc.  All Rights
-- Reserved.  Reproduction of this document is authorized on
-- condition that the foregoing copyright notice is included.
-- This SynOptics SNMP Management Information Base Specification
-- (Specification) embodies SynOptics' confidential and
-- proprietary intellectual property.  SynOptics retains all
-- title and ownership in the Specification, including any
-- revisions.  
--
-- It is SynOptics intent to encourage the widespread use of
-- this Specification in connection with the management of
-- SynOptics products. SynOptics grants vendors, end-users,
-- and other interested parties a non-exclusive license to
-- use this Specification in connection with the management
-- of SynOptics products.
--
-- This Specification is supplied "AS IS," and SynOptics makes
-- no warranty, either express or implied, as to the use,
-- operation, condition, or performance of the Specification.


DEFINITIONS ::= BEGIN

-- SECTION 1: Top Level Definitions

-- Imports

IMPORTS
	snmp, ifIndex, egpNeighAddr
					FROM RFC1213-MIB
	TRAP-TYPE			FROM RFC-1215
	synoptics, s3ChassisPsStatus,
	s3ChassisFanStatus, s3CommonBoardPsStatus
					FROM SYNOPTICS-COMMON-MIB
	s3EnetBoardStatus, s3EnetBoardPsStatus,
	s3EnetPortPartStatus, s3EnetPortJabberStatus,
	s3EnetLocBridgePortOpSts, s3EnetLocBridgeDiagSts,
	s3EnetRemBridgePortOpSts, s3EnetRemBridgeDiagSts,
	s3EnetRouterStandbySts, s3EnetRouterDiagSts
					FROM SYNOPTICS-ETHERNET-MIB
	ieee8023PromRxStatus
					FROM SYNOPTICS-IEEE8023-MIB
	s3TrNmmRingNum, s3TrNodeEntUna,
	s3TrNodeEntBeaconType, s3TrNodeEntPhysDrop
					FROM SYNOPTICS-TOKENRING-MIB;

-- SECTION 2: Generic Trap Definitions


coldStart TRAP-TYPE
	ENTERPRISE	snmp
--	STATUS		mandatory for all SynOptics agents
	DESCRIPTION
		"A coldStart trap signifies that the sending protocol entity 
		is reinitializing itself such that the agent's configuration 
		or the protocol entity implementation may be altered."
	::= 0

warmStart TRAP-TYPE
	ENTERPRISE	snmp
--	STATUS		implemented by TR 3.1 only, not supported in future
	DESCRIPTION
		"A warmStart trap signifies that the sending protocol entity 
		is reinitializing itself such that neither the agent 
		configuration nor the protocol entity implementation is 
		altered."
	::= 1

linkDown TRAP-TYPE
	ENTERPRISE	snmp
	VARIABLES	{ ifIndex }
--	STATUS		not used by TR or Enet
	DESCRIPTION
		"A linkDown trap signifies that the sending protocol entity 
		recognizes a failure in one of the communication links 
		represented in the agent's configuration."
	::= 2

linkUp TRAP-TYPE
	ENTERPRISE	snmp
	VARIABLES	{ ifIndex }
--	STATUS		not used by TR or Enet
	DESCRIPTION
		"A linkUp trap signifies that the sending protocol entity 
		recognizes that one of the communication links represented in 
		the agent's configuration has come up."
	::= 3

authenticationFailure TRAP-TYPE
	ENTERPRISE	snmp
--	STATUS		mandatory for all SynOptics agents
	DESCRIPTION
		"An authenticationFailure trap signifies that the sending 
		protocol entity is the addressee of a protocol message that is
		not properly authenticated. While implementations of the SNMP 
		must be capable of generating this trap, they must also be 
		capable of suppressing the emission of such traps via an 
		implementation-specific mechanism."
	::= 4

egpNeighborLoss TRAP-TYPE
	ENTERPRISE	snmp
	VARIABLES	{ egpNeighAddr }
--	STATUS		mandatory if EGP implemented (routers only)
	DESCRIPTION
		"An egpNeighborLoss trap signifies that an EGP neighbor for 
		whom the sending protocol entity was an EGP peer has been 
		marked down and the peer relationship no longer obtains."
	::= 5

-- SECTION 3: SynOptics Enterprise Trap Definitions



chassisPowerSupplyFailure TRAP-TYPE
	ENTERPRISE	synoptics
	VARIABLES	{ s3ChassisPsStatus }
--	STATUS		mandatory for all SynOptics agents
	DESCRIPTION
		"Concentrator power supply failure."
	::= 0		-- 0x00

chassisFanFailure TRAP-TYPE
	ENTERPRISE	synoptics
	VARIABLES	{ s3ChassisFanStatus }
--	STATUS		mandatory for all SynOptics agents
	DESCRIPTION
		"Concentrator fan failure."
	::= 1		-- 0x01

boardFailure TRAP-TYPE
	ENTERPRISE	synoptics
	VARIABLES	{ s3EnetBoardStatus }
--	STATUS		mandatory for 3.x Ethernet agents.
	DESCRIPTION
		"General board failure detected by Ethernet NMM."
	::= 2		-- 0x02

enetBoardPowerSupplyFailure TRAP-TYPE
	ENTERPRISE	synoptics
	VARIABLES	{ s3EnetBoardPsStatus }
--	STATUS		mandatory for 3.x Ethernet agents.
--				Token ring agents use
--				boardPowerSupplyFailure (27) instead.
	DESCRIPTION
		"Ethernet board power supply failure."
	::= 3		-- 0x03

portAutoPartition TRAP-TYPE
	ENTERPRISE	synoptics
	VARIABLES	{ s3EnetPortPartStatus, s3EnetPortJabberStatus }
--	STATUS		mandatory for all Ethernet agents
	DESCRIPTION
		"Port auto partitions."
	::= 4		-- 0x04

portDTEJabbering TRAP-TYPE
	ENTERPRISE	synoptics
	VARIABLES	{ s3EnetPortJabberStatus }
--	STATUS		mandatory for all Ethernet agents
	DESCRIPTION
		"Ethernet DTE jabbering detected."
	::= 5		-- 0x05

nmmSaturation TRAP-TYPE
	ENTERPRISE	synoptics
	VARIABLES	{ ieee8023PromRxStatus }
--	STATUS		mandatory for 3.x Ethernet agents
	DESCRIPTION
		"NMM is dropping packets due to overload."
	::= 6		-- 0x06

localBridgePortOperationChanged TRAP-TYPE
	ENTERPRISE	synoptics
	VARIABLES	{ s3EnetLocBridgePortOpSts }
--	STATUS		mandatory for 3.x Ethernet agents
	DESCRIPTION
		"Bridge changes from standby <-> operation."
	::= 7		-- 0x07

localBridgeDiagnostic TRAP-TYPE
	ENTERPRISE	synoptics
	VARIABLES	{ s3EnetLocBridgeDiagSts }
--	STATUS		mandatory for 3.x Ethernet agents
	DESCRIPTION
		"NMM detects bridge failure."
	::= 8		-- 0x08

remoteBridgePortOperationChanged TRAP-TYPE
	ENTERPRISE	synoptics
	VARIABLES	{ s3EnetRemBridgePortOpSts }
--	STATUS		mandatory for 3.x Ethernet agents
	DESCRIPTION
		"Bridge changes from standby <-> operation."
	::= 9		-- 0x09

remoteBridgeDiagnostic TRAP-TYPE
	ENTERPRISE	synoptics
	VARIABLES	{ s3EnetRemBridgeDiagSts }
--	STATUS		mandatory for 3.x Ethernet agents
	DESCRIPTION
		"NMM detects remote bridge failure."
	::= 10		-- 0x0a

stationBeacons TRAP-TYPE
	ENTERPRISE	synoptics
	VARIABLES	{ s3TrNmmRingNum, s3TrNodeEntUna, 
			  s3TrNodeEntBeaconType }
--	STATUS		mandatory for all Token Ring agents
	DESCRIPTION
		"Station on the ring is beaconing."
	::= 14		-- 0x0e

newActMonDetect TRAP-TYPE
	ENTERPRISE	synoptics
	VARIABLES	{ s3TrNmmRingNum,
			  s3TrNodeEntUna, s3TrNodeEntPhysDrop }
--	STATUS		mandatory for all Token Ring agents
	DESCRIPTION
		"A new active monitor has been detected."
	::= 22		-- 0x16


boardPowerSupplyFailure TRAP-TYPE
	ENTERPRISE	synoptics
	VARIABLES	{ s3CommonBoardPsStatus }
--	STATUS		mandatory for all Token Ring agents
	DESCRIPTION
		"Board power supply failure."
	::= 27		-- 0x1b

routerOperationChanged TRAP-TYPE
	ENTERPRISE	synoptics
	VARIABLES	{ s3EnetRouterStandbySts }
--	STATUS		mandatory for 3.3 Ethernet agents
	DESCRIPTION
		"Router changes from standby <-> operation."
	::= 33		-- 0x21

routerDiagnostic TRAP-TYPE
	ENTERPRISE	synoptics
	VARIABLES	{ s3EnetRouterDiagSts }
--	STATUS		mandatory for 3.3 Ethernet agents
	DESCRIPTION
		"NMM detects router failure."
	::= 34		-- 0x22

END
