XYPLEX-BOOT-CLIENT-MIB DEFINITIONS ::= BEGIN
            
                    IMPORTS
                            enterprises
                                    FROM RFC1155-SMI
                            DisplayString
                                    FROM RFC1158-MIB
                            OBJECT-TYPE
                                    FROM RFC1212-CONCISE-MIB;
            
            xyplex          OBJECT IDENTIFIER ::= { enterprises 33 }
            bootClient      OBJECT IDENTIFIER ::= { xyplex 12 }
            
            --  This MIB module uses the extended OBJECT-TYPE macro as
            --  defined in [9]
            
            --  this is the MIB module for clients of Xyplex bootstrap
            --  service
            
            
            -- the Bootstrap Client group
            
            -- Implementation of this group is mandatory for all Xyplex
            -- systems that use the Xyplex bootstrap service
            
            bootClientStatus OBJECT-TYPE
--                SYNTAX DisplayString (SIZE (0..1400))
--                ACCESS read-only
--                STATUS mandatory
--               DESCRIPTION
--                    "The overall status of the bootstrapping operation, 
--                    including, for example, what is presently happening 
--                    and error information."
                ::= { bootClient, 1 }
            
END
