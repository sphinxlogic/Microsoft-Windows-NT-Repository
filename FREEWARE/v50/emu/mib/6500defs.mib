-- Version 1.1.1.2, modified 3/24/94

          CDX6500-SMI DEFINITIONS ::= BEGIN

          EXPORTS -- Pegasus Group Object Identifiers
                  cdx6500NodeMgmt, cdx6500Configuration, cdx6500Statistics,
                  cdx6500Controls,
                  cdx6500NMSNMPGroup, cdx6500NMNodeParametersGroup,
                  cdx6500NMDiagnosticsGroup, cdx6500NMControlsGroup,
                  cdx6500NMDLSVGroup,
                  cdx6500CfgProtocolGroup, cdx6500CfgGeneralGroup,
                  cdx6500PCTPortProtocolGroup, cdx6500PCTMuxChannelGroup, 
                  cdx6500PCTStationProtocolGroup, cdx6500PCTBSC3270DeviceGroup,
                  cdx6500PCTRouterGroup, cdx6500PCTBridgeGroup,
                  cdx6500PCTNCRBSCDeviceGroup,
                  cdx6500StatProtocolGroup, cdx6500StatOtherStatsGroup,
                  cdx6500StatPortGroup, cdx6500StatStationGroup, 
                  cdx6500StatTFTPGroup,
                  cdx6500PSTPortProtocolGroup, cdx6500PSTMuxChannelGroup,
                  cdx6500PSTStationProtocolGroup, cdx6500PSTRouterGroup,
                  cdx6500PSTBridgeGroup, cdx6500PSTLANConnectionGroup,
                  cdx6500ContPortControl, cdx6500ContSDLCStationTable,
                  cdx6500ContWANAdaptor, cdx6500ContTFTP, cdx6500dsdControls,
                  cdx6500statControls, cdx6500ContSDLC, cdx6500ContMX25,
                  cdx6500ContXDLC,
                  Counter16, Counter8;

          -- Pegasus-specific textual conventions

                  -- Counter16 type is for two-byte objects that wraparound at
                  -- 65535
                  Counter16 ::=
                        INTEGER (0..65535)

                  -- Counter8 type is for two-byte objects that wraparound at
                  -- 255
                  Counter8 ::=
                        INTEGER (0..255)


          --  Motorola/Codex private enterprise MIB

          -- internet            OBJECT IDENTIFIER ::= { iso org(3) dod(6) 1 }
          -- private             OBJECT IDENTIFIER ::= { internet 4 }
          -- enterprises         OBJECT IDENTIFIER ::= { private 1 }
          codex               OBJECT IDENTIFIER ::= { enterprises 449 }
          cdxProductSpecific  OBJECT IDENTIFIER ::= { codex 2 }
          cdx6500             OBJECT IDENTIFIER ::= { cdxProductSpecific 1 }

          -- groups in Pegasus MIB

          cdx6500NodeMgmt       OBJECT IDENTIFIER ::= { cdx6500 1 }
          cdx6500Configuration  OBJECT IDENTIFIER ::= { cdx6500 2 }
          cdx6500Statistics     OBJECT IDENTIFIER ::= { cdx6500 3 }
          cdx6500Controls       OBJECT IDENTIFIER ::= { cdx6500 4 }

          -- Pegasus Node Management Groups (NM)

          cdx6500NMSNMPGroup             OBJECT IDENTIFIER ::= { cdx6500NodeMgmt 1 }
          cdx6500NMNodeParametersGroup   OBJECT IDENTIFIER ::= { cdx6500NodeMgmt 2 }
          cdx6500NMDiagnosticsGroup      OBJECT IDENTIFIER ::= { cdx6500NodeMgmt 3 }
          cdx6500NMControlsGroup         OBJECT IDENTIFIER ::= { cdx6500NodeMgmt 4 }
          cdx6500NMDLSVGroup             OBJECT IDENTIFIER ::= { cdx6500NodeMgmt 5 }

          -- Pegasus Configuration Groups (Cfg)

          cdx6500CfgProtocolGroup  OBJECT IDENTIFIER ::= { cdx6500Configuration 1 }
          cdx6500CfgGeneralGroup   OBJECT IDENTIFIER ::= { cdx6500Configuration 2 }

          -- Pegasus Protocol Configuration Tables (PCT)

          cdx6500PCTPortProtocolGroup      OBJECT IDENTIFIER ::= { cdx6500CfgProtocolGroup 1 }
          cdx6500PCTStationProtocolGroup   OBJECT IDENTIFIER ::= { cdx6500CfgProtocolGroup 3 }
          cdx6500PCTBSC3270DeviceGroup     OBJECT IDENTIFIER ::= { cdx6500CfgProtocolGroup 4 }
          cdx6500PCTRouterGroup            OBJECT IDENTIFIER ::= { cdx6500CfgProtocolGroup 5 }
          cdx6500PCTBridgeGroup            OBJECT IDENTIFIER ::= { cdx6500CfgProtocolGroup 6 }
          cdx6500PCTNCRBSCDeviceGroup      OBJECT IDENTIFIER ::= { cdx6500CfgProtocolGroup 7 }
          cdx6500PCTBSTDDeviceGroup        OBJECT IDENTIFIER ::= { cdx6500CfgProtocolGroup 8 }

          -- Pegasus Statistics Group (Stat)

          cdx6500StatProtocolGroup       OBJECT IDENTIFIER ::= { cdx6500Statistics 1 }
          cdx6500StatOtherStatsGroup     OBJECT IDENTIFIER ::= { cdx6500Statistics 2 }
          cdx6500StatTFTPGroup           OBJECT IDENTIFIER ::= { cdx6500Statistics 3 }

          -- Protocol Statistics Tables (PST)

          cdx6500PSTPortProtocolGroup      OBJECT IDENTIFIER ::= { cdx6500StatProtocolGroup 1 }
          cdx6500PSTStationProtocolGroup   OBJECT IDENTIFIER ::= { cdx6500StatProtocolGroup 3 }
          cdx6500PSTRouterGroup            OBJECT IDENTIFIER ::= { cdx6500StatProtocolGroup 4 }
          cdx6500PSTBridgeGroup            OBJECT IDENTIFIER ::= { cdx6500StatProtocolGroup 5 }
          cdx6500PSTLANConnectionGroup     OBJECT IDENTIFIER ::= { cdx6500StatProtocolGroup 6 }
                  

          -- Pegasus Controls Group (Cont)

          cdx6500ContWANAdaptor                 OBJECT IDENTIFIER ::= { cdx6500Controls 1 }
          cdx6500ContTFTP                       OBJECT IDENTIFIER ::= { cdx6500Controls 2 }
          cdx6500dsdControls                    OBJECT IDENTIFIER ::= { cdx6500Controls 3 }
          cdx6500statControls                	OBJECT IDENTIFIER ::= { cdx6500Controls 4 }
          cdx6500ContSDLC                       OBJECT IDENTIFIER ::= { cdx6500Controls 5 }
          cdx6500ContMX25                       OBJECT IDENTIFIER ::= { cdx6500Controls 6 }
          cdx6500ContXDLC                       OBJECT IDENTIFIER ::= { cdx6500Controls 7 }
END
