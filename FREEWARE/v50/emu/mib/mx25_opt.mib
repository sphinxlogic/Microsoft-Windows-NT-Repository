-- Version 1.2.1.2, modified 3/10/94

	MX25-OPT-MIB DEFINITIONS ::= BEGIN

	IMPORTS
		-- standard imports from SMI files

			mgmt, NetworkAddress, IpAddress, Counter, Gauge,
			TimeTicks
				FROM RFC1155-SMI
			OBJECT-TYPE
				FROM RFC-1212

		-- imports from pegasus_common.mib specific to this module. Should
		-- include Configuration, Statistics, and Control groups, as 
		-- applicable. The two imports listed below are *examples*.

			cdx6500PCTPortProtocolGroup,
			cdx6500PSTPortProtocolGroup,
			cdx6500PCTStationProtocolGroup,
			cdx6500PSTStationProtocolGroup
				FROM CDX6500-SMI;

	--	This MIB module uses the extended OBJECT-TYPE macro as
	--	defined in [14];


	-- textual conventions
		-- These are "aliases" for commonly-used variants of the four primitive
		-- object types provided by SNMP and also for user-defined object types.
		-- Any definitions provided here are good only in this MIB, unless
		-- explicitly listed as EXPORTs. DisplayString and PhysAddress are
		-- commonly used textual conventions.

	DisplayString ::=
		OCTET STRING
	-- This data type is used to model textual information taken
	-- from the NVT ASCII character set.	By convention, objects
	-- with this syntax are declared as having
	--
	--	 SIZE (0..255)

	PhysAddress ::=
		OCTET STRING
	-- This data type is used to model media addresses.	For many
	-- types of media, this will be in a binary representation.
	-- For example, an ethernet address would be represented as
	-- a string of 6 octets.



	-- The MX25 Port Configuration Tables
	-- These tables contain Configuration paramaters 
	-- for the MX25 Port table.
			
	cdx6500PPCTMX25PortTables	OBJECT IDENTIFIER ::= { cdx6500PCTPortProtocolGroup 4 }


	-- The MX25 Port Configuration Table
	-- This table contains all common Configuration
	-- paramaters for the MX25 Port table.
			
	cdx6500PPCTMX25PortTable OBJECT-TYPE
		SYNTAX		SEQUENCE OF Cdx6500PPCTMX25PortEntry
		ACCESS		not-accessible
		STATUS		mandatory
		DESCRIPTION
			"All of the common configuration parameters relevant
			 to the MX.25 port table."
		::= { cdx6500PPCTMX25PortTables 1 }
			
	cdx6500PPCTMX25PortEntry OBJECT-TYPE
		SYNTAX		Cdx6500PPCTMX25PortEntry
		ACCESS		not-accessible
		STATUS		mandatory
		DESCRIPTION
			"A row of MX.25 Port configuration parameters."
		INDEX	{ cdx6500mx25pCfgPortNum }
		::= { cdx6500PPCTMX25PortTable 1 }
			
	Cdx6500PPCTMX25PortEntry ::=
		SEQUENCE {
			cdx6500mx25pCfgPortNum
				INTEGER,
			cdx6500mx25pSubType
				INTEGER
			}
	cdx6500mx25pCfgPortNum OBJECT-TYPE
		SYNTAX		INTEGER (1..54)
		ACCESS		read-only
		STATUS		mandatory
		DESCRIPTION
			"MX25 Port Number"
		DEFVAL { 1 }
		::= { cdx6500PPCTMX25PortEntry 1 }
			
	cdx6500mx25pSubType OBJECT-TYPE
		SYNTAX		INTEGER {
					master(0),
					slave(1)
					}
		ACCESS		read-only
		STATUS		mandatory
		DESCRIPTION
			"This is the mode in which this MX25 port will run."
		DEFVAL { master }
		::= { cdx6500PPCTMX25PortEntry 2 }
			




	-- The MX25 Master Port Configuration Table
	-- This table contains Configuration paramaters 
	-- for the MX25 Master Port table.
			
	cdx6500PPCTMX25MPortTable OBJECT-TYPE
		SYNTAX		SEQUENCE OF Cdx6500PPCTMX25MPortEntry
		ACCESS		not-accessible
		STATUS		mandatory
		DESCRIPTION
			"All of the configuration parameters relevant
			 to the MX.25 Master port table."
		::= { cdx6500PPCTMX25PortTables 2 }
			
	cdx6500PPCTMX25MPortEntry OBJECT-TYPE
		SYNTAX		Cdx6500PPCTMX25MPortEntry
		ACCESS		not-accessible
		STATUS		mandatory
		DESCRIPTION
			"A row of MX.25 Master Port configuration parameters."
		INDEX	{ cdx6500mx25mpCfgPortNum }
		::= { cdx6500PPCTMX25MPortTable 1 }
			
	Cdx6500PPCTMX25MPortEntry ::=
		SEQUENCE {
			cdx6500mx25mpCfgPortNum
				INTEGER,
			cdx6500mx25mpSubType
				INTEGER,
			cdx6500mx25mpClockSource
				INTEGER,
			cdx6500mx25mpClockSpeed
				INTEGER,
			cdx6500mx25mpStationCnt
				INTEGER,
			cdx6500mx25mpPollTimer
				INTEGER,
			cdx6500mx25mpPollPeriod
				INTEGER,
			cdx6500mx25mpTries
				INTEGER,
			cdx6500mx25mpRestartTimer
				INTEGER,
			cdx6500mx25mpResetTimer
				INTEGER,
			cdx6500mx25mpCallTimer
				INTEGER,
			cdx6500mx25mpClearTimer
				INTEGER,
			cdx6500mx25mpPortControl
				DisplayString,
			cdx6500mx25mpTXEncoding
				INTEGER
			}
			
	cdx6500mx25mpCfgPortNum OBJECT-TYPE
		SYNTAX		INTEGER (1..54)
		ACCESS		read-only
		STATUS		mandatory
		DESCRIPTION
			"MX25 Port Number"
		DEFVAL { 1 }
		::= { cdx6500PPCTMX25MPortEntry 1 }
			
	cdx6500mx25mpSubType OBJECT-TYPE
		SYNTAX		INTEGER {
					master(0)
					}
		ACCESS		read-only
		STATUS		mandatory
		DESCRIPTION
			"This is the mode in which this MX25 port will run."
		DEFVAL { Master }
		::= { cdx6500PPCTMX25MPortEntry 2 }
			
	cdx6500mx25mpClockSource OBJECT-TYPE
		SYNTAX		INTEGER {
					int(0),
					ext(1)
					}
		ACCESS		read-only
		STATUS		mandatory
		DESCRIPTION
			"int - internal clock source
			ext - external clock source"
		DEFVAL { EXT }
		::= { cdx6500PPCTMX25MPortEntry 3 }
			
	cdx6500mx25mpClockSpeed OBJECT-TYPE
		SYNTAX		INTEGER (1200..80000)
		ACCESS		read-only
		STATUS		mandatory
		DESCRIPTION
			"This is the speed of the port in bits per second, when using
			internal clocking."
		DEFVAL { 9600 }
		::= { cdx6500PPCTMX25MPortEntry 4 }
			
	cdx6500mx25mpStationCnt OBJECT-TYPE
		SYNTAX		INTEGER (1..32)
		ACCESS		read-only
		STATUS		mandatory
		DESCRIPTION
			"The number of slave stations on the MX25 line."
		DEFVAL { 4 }
		::= { cdx6500PPCTMX25MPortEntry 5 }
			
	cdx6500mx25mpPollTimer OBJECT-TYPE
		SYNTAX		INTEGER (1..255)
		ACCESS		read-only
		STATUS		mandatory
		DESCRIPTION
			"Worst case delay for a slave to respond to a poll frame sent by
			the master, including modem turn around time, etc.
			Value in 10ths of second ( 30 = 3.0 seconds )."
		DEFVAL { 30 }
		::= { cdx6500PPCTMX25MPortEntry 6 }
			
	cdx6500mx25mpPollPeriod OBJECT-TYPE
		SYNTAX		INTEGER (50..250)
		ACCESS		read-only
		STATUS		mandatory
		DESCRIPTION
			"Time in milliseconds between polls when no data is exchanged."
		DEFVAL { 50 }
		::= { cdx6500PPCTMX25MPortEntry 7 }
			
	cdx6500mx25mpTries OBJECT-TYPE
		SYNTAX		INTEGER (1..16)
		ACCESS		read-only
		STATUS		mandatory
		DESCRIPTION
			"Maximum number of attempts to complete a transmission."
		DEFVAL { 10 }
		::= { cdx6500PPCTMX25MPortEntry 8 }
			
	cdx6500mx25mpRestartTimer OBJECT-TYPE
		SYNTAX		INTEGER (5..255)
		ACCESS		read-only
		STATUS		mandatory
		DESCRIPTION
			"Restart-Request timeout timer in seconds. If timer expires, request
			is sent again."
		DEFVAL { 180 }
		::= { cdx6500PPCTMX25MPortEntry 9 }
			
	cdx6500mx25mpResetTimer OBJECT-TYPE
		SYNTAX		INTEGER (5..255)
		ACCESS		read-only
		STATUS		mandatory
		DESCRIPTION
			"Reset-Request timeout timer in seconds. If timer expires, request
			is sent again."
		DEFVAL { 180 }
		::= { cdx6500PPCTMX25MPortEntry 10 }
			
	cdx6500mx25mpCallTimer OBJECT-TYPE
		SYNTAX		INTEGER (5..200)
		ACCESS		read-only
		STATUS		mandatory
		DESCRIPTION
			"Call-Request timeout timer in seconds. If timer expires, call
			is cleared."
		DEFVAL { 200 }
		::= { cdx6500PPCTMX25MPortEntry 11 }
			
	cdx6500mx25mpClearTimer OBJECT-TYPE
		SYNTAX		INTEGER (5..255)
		ACCESS		read-only
		STATUS		mandatory
		DESCRIPTION
			"Clear-Request timeout timer in seconds. If timer expires, request
			is sent again."
		DEFVAL { 180 }
		::= { cdx6500PPCTMX25MPortEntry 12 }
			
	cdx6500mx25mpPortControl OBJECT-TYPE
		SYNTAX		DisplayString (SIZE(2..8))
		ACCESS		read-only
		STATUS		mandatory
		DESCRIPTION
			"Specify any of the following port control options:

			NONE  - no option specified
			MB    - raise Pin 22 when the port becomes disabled"
		DEFVAL { NONE }
		::= { cdx6500PPCTMX25MPortEntry 13 }
			
	cdx6500mx25mpTXEncoding OBJECT-TYPE
		SYNTAX		INTEGER {
					nrz(0),
					nrzi(1)
					}
		ACCESS		read-only
		STATUS		mandatory
		DESCRIPTION
			"This is the data encoding used on the MX25 link.

			nrz  - Non Return to Zero
			nrzi - Non Return to Zero Inverted"
		DEFVAL { nrz }
		::= { cdx6500PPCTMX25MPortEntry 14 }
			




	-- The MX25 Slave Port Configuration Table
	-- This table contains Configuration paramaters 
	-- for the MX25 Slave Port table.
			
	cdx6500PPCTMX25SPortTable OBJECT-TYPE
		SYNTAX		SEQUENCE OF Cdx6500PPCTMX25SPortEntry
		ACCESS		not-accessible
		STATUS		mandatory
		DESCRIPTION
			"All of the configuration parameters relevant
			 to the MX.25 Slave port table."
		::= { cdx6500PPCTMX25PortTables 3 }
			
	cdx6500PPCTMX25SPortEntry OBJECT-TYPE
		SYNTAX		Cdx6500PPCTMX25SPortEntry
		ACCESS		not-accessible
		STATUS		mandatory
		DESCRIPTION
			"A row of MX.25 Slave Port configuration parameters."
		INDEX	{ cdx6500mx25spCfgPortNum }
		::= { cdx6500PPCTMX25SPortTable 1 }
			
	Cdx6500PPCTMX25SPortEntry ::=
		SEQUENCE {
			cdx6500mx25spCfgPortNum
				INTEGER,
			cdx6500mx25spSubType
				INTEGER,
			cdx6500mx25spClockSource
				INTEGER,
			cdx6500mx25spClockSpeed
				INTEGER,
			cdx6500mx25spStationAddress
				DisplayString,
			cdx6500mx25spPVCChannels
				INTEGER,
			cdx6500mx25spStartingPVC
				INTEGER,
			cdx6500mx25spSVCChannels
				INTEGER,
			cdx6500mx25spStartingSVC
				INTEGER,
			cdx6500mx25spPollTimer
				INTERGER,
			cdx6500mx25spTries
				INTEGER,
			cdx6500mx25spFrameWinSize
				INTEGER,
			cdx6500mx25spPacketWinSize
				INTEGER,
			cdx6500mx25spRestartTimer
				INTEGER,
			cdx6500mx25spResetTimer
				INTEGER,
			cdx6500mx25spCallTimer
				INTEGER,
			cdx6500mx25spClearTimer
				INTEGER,
			cdx6500mx25spMX25Options
				DisplayString,
			cdx6500mx25spRCDestination
				DisplayString,
			cdx6500mx25spCUG
				DisplayString,
			cdx6500mx25spBillingRecords
				INTEGER,
			cdx6500mx25spPortControl
				DisplayString,
			cdx6500mx25spTXEncoding
				INTEGER,
			cdx6500mx25spUpperQueue
				INTEGER,
			cdx6500mx25spLowerQueue
				INTEGER
			}
			
	cdx6500mx25spCfgPortNum OBJECT-TYPE
		SYNTAX		INTEGER (1..54)
		ACCESS		read-only
		STATUS		mandatory
		DESCRIPTION
			"MX25 Port Number"
		DEFVAL { 1 }
		::= { cdx6500PPCTMX25SPortEntry 1 }
			
	cdx6500mx25spSubType OBJECT-TYPE
		SYNTAX		INTEGER {
					slave(1)
					}
		ACCESS		read-only
		STATUS		mandatory
		DESCRIPTION
			"This is the mode in which this MX25 port will run."
		DEFVAL { Slave }
		::= { cdx6500PPCTMX25SPortEntry 2 }
			
	cdx6500mx25spClockSource OBJECT-TYPE
		SYNTAX		INTEGER {
					int(0),
					ext(1)
					}
		ACCESS		read-only
		STATUS		mandatory
		DESCRIPTION
			"int - internal clock source
			ext - external clock source"
		DEFVAL { ext }
		::= { cdx6500PPCTMX25SPortEntry 3 }
			
	cdx6500mx25spClockSpeed OBJECT-TYPE
		SYNTAX		INTEGER (1200..80000)
		ACCESS		read-only
		STATUS		mandatory
		DESCRIPTION
			"This is the speed of the port in bits per second, when using
			internal clocking."
		DEFVAL { 9600 }
		::= { cdx6500PPCTMX25SPortEntry 4 }
			
	cdx6500mx25spStationAddress OBJECT-TYPE
		SYNTAX		DisplayString (SIZE(0..2))
		ACCESS		read-only
		STATUS		mandatory
		DESCRIPTION
			"The station address on the multidrop line."
		DEFVAL { 04 }
		::= { cdx6500PPCTMX25SPortEntry 5 }
			
	cdx6500mx25spPVCChannels OBJECT-TYPE
		SYNTAX		INTEGER (0..128)
		ACCESS		read-only
		STATUS		mandatory
		DESCRIPTION
			"Number of logical channels used for Permanent Virtual Circuits.
			The total number of PVC and SVC channels on a link should be kept as
			small as possible and consistent with needs.
			PVC connections must be configured in the PVC Table."
		DEFVAL { 0 }
		::= { cdx6500PPCTMX25SPortEntry 6 }
			
	cdx6500mx25spStartingPVC OBJECT-TYPE
		SYNTAX		INTEGER (1..255)
		ACCESS		read-only
		STATUS		mandatory
		DESCRIPTION
			"This is the starting logical channel number for the Permanent Virtual
			Circuits on this link. Not used if the number of PVCs = 0."
		DEFVAL { 1 }
		::= { cdx6500PPCTMX25SPortEntry 7 }
			
	cdx6500mx25spSVCChannels OBJECT-TYPE
		SYNTAX		INTEGER (0..255)
		ACCESS		read-only
		STATUS		mandatory
		DESCRIPTION
			"Number of logical channels used in Switched Virtual Circuits.
			The total number of PVC and SVC channels on a link should be kept as
			small as possible and consistent with needs."
		DEFVAL { 16 }
		::= { cdx6500PPCTMX25SPortEntry 8 }
			
	cdx6500mx25spStartingSVC OBJECT-TYPE
		SYNTAX		INTEGER (0..255)
		ACCESS		read-only
		STATUS		mandatory
		DESCRIPTION
			"This is the starting logical channel number for the Switched Virtual
			Circuits on this link. Not used if the number of SVCs = 0."
		DEFVAL { 1 }
		::= { cdx6500PPCTMX25SPortEntry 9 }
			
	cdx6500mx25spPollTimer OBJECT-TYPE
		SYNTAX		INTEGER (1..255)
		ACCESS		read-only
		STATUS		mandatory
		DESCRIPTION
			"Worst case delay for a slave to respond to a poll frame sent by
			the master, including modem turn around time, etc.
			Value in 10ths of second ( 30 = 3.0 seconds )."
		DEFVAL { 30 }
		::= { cdx6500PPCTMX25SPortEntry 10 }
			
	cdx6500mx25spTries OBJECT-TYPE
		SYNTAX		INTEGER (1..16)
		ACCESS		read-only
		STATUS		mandatory
		DESCRIPTION
			"Maximum number of attempts to complete a transmission."
		DEFVAL { 10 }
		::= { cdx6500PPCTMX25SPortEntry 11 }
			
	cdx6500mx25spFrameWinSize OBJECT-TYPE
		SYNTAX		INTEGER (1..7)
		ACCESS		read-only
		STATUS		mandatory
		DESCRIPTION
			"Frame level window size must be set to the same value in
			devices at each end of the link."
		DEFVAL { 7 }
		::= { cdx6500PPCTMX25SPortEntry 12 }
			
	cdx6500mx25spPacketWinSize OBJECT-TYPE
		SYNTAX		INTEGER (1..7)
		ACCESS		read-only
		STATUS		mandatory
		DESCRIPTION
			"Packet level window size must be set to the same value in
			devices at each end of the link."
		DEFVAL { 2 }
		::= { cdx6500PPCTMX25SPortEntry 13 }
			
	cdx6500mx25spRestartTimer OBJECT-TYPE
		SYNTAX		INTEGER (5..255)
		ACCESS		read-only
		STATUS		mandatory
		DESCRIPTION
			"Restart-Request timeout timer in seconds. If timer expires, request
			is sent again."
		DEFVAL { 180 }
		::= { cdx6500PPCTMX25SPortEntry 14 }
			
	cdx6500mx25spResetTimer OBJECT-TYPE
		SYNTAX		INTEGER (5..255)
		ACCESS		read-only
		STATUS		mandatory
		DESCRIPTION
			"Reset-Request timeout timer in seconds. If timer expires, request
			is sent again."
		DEFVAL { 180 }
		::= { cdx6500PPCTMX25SPortEntry 15 }
			
	cdx6500mx25spCallTimer OBJECT-TYPE
		SYNTAX		INTEGER (5..200)
		ACCESS		read-only
		STATUS		mandatory
		DESCRIPTION
			"Call-Request timeout timer in seconds. If timer expires, call
			is cleared."
		DEFVAL { 200 }
		::= { cdx6500PPCTMX25SPortEntry 16 }
			
	cdx6500mx25spClearTimer OBJECT-TYPE
		SYNTAX		INTEGER (5..255)
		ACCESS		read-only
		STATUS		mandatory
		DESCRIPTION
			"Clear-Request timeout timer in seconds. If timer expires, request
			is sent again."
		DEFVAL { 180 }
		::= { cdx6500PPCTMX25SPortEntry 17 }
			
	cdx6500mx25spMX25Options OBJECT-TYPE
		SYNTAX		DisplayString (SIZE(3..22))
		ACCESS		read-only
		STATUS		mandatory
		DESCRIPTION
			"Select options on this MX.25 port as follows:

			NONE  - no option specified
			HOLD  - hold calls over link restart
			CUG   - check closed user group; otherwise, CUG passes transparently
			INL   - inter-node link. Link goes to another 6500 device
			INLA  - set with INL option when an MX.25 link connection is to
			        a 6500 node using 2.12.04 or earlier
                        DELAY - enable Delay and Path trace on this link (link
                                must connected to Rel. 4.xx node)

			Any combination of the above specified by summing
			(e.g. HOLD+CUG+. . .)."
		DEFVAL { "NONE" }
		::= { cdx6500PPCTMX25SPortEntry 18 }
			
	cdx6500mx25spRCDestination OBJECT-TYPE
		SYNTAX		DisplayString (SIZE(0..32))
		ACCESS		read-only
		STATUS		mandatory
		DESCRIPTION
			"All calls entering this port will be routed to the destination
			specified in this parameter, irrespective of route selection table
			entries. For example, to route calls to port 1, use P1.
			To route calls to port 2, station 4, use P2S4.
			Blank this field to disable this function."
		DEFVAL { '20'H } -- blank
		::= { cdx6500PPCTMX25SPortEntry 19 }
			
	cdx6500mx25spCUG OBJECT-TYPE
		SYNTAX		DisplayString (SIZE(0..23))
		ACCESS		read-only
		STATUS		mandatory
		DESCRIPTION
			"The port may be a member of up to 8 different Closed User
			Groups (CUGs). Each CUG membership must be a two digit number
			(except --) and separated by a comma. ( e.g. 12,34,56,09,02,03 ).

			--    - No CUG Membership
			00-99 - CUG Membership"
		::= { cdx6500PPCTMX25SPortEntry 20 }
			
	cdx6500mx25spBillingRecords OBJECT-TYPE
		SYNTAX		INTEGER {
					off(0),
					on(1)
					}
		ACCESS		read-only
		STATUS		mandatory
		DESCRIPTION
			"This controls whether billing (accounting) records will be created for
			calls on this port."
		DEFVAL { off }
		::= { cdx6500PPCTMX25SPortEntry 21 }
			
	cdx6500mx25spPortControl OBJECT-TYPE
		SYNTAX		DisplayString (SIZE(2..8))
		ACCESS		read-only
		STATUS		mandatory
		DESCRIPTION
			"Specify any of the following port control options:

			NONE  - no option specified
			MB    - raise Pin 22 when the port becomes disabled"
		DEFVAL { "NONE" }
		::= { cdx6500PPCTMX25SPortEntry 22 }
			
	cdx6500mx25spTXEncoding OBJECT-TYPE
		SYNTAX		INTEGER {
					nrz(0),
					nrzi(1)
					}
		ACCESS		read-only
		STATUS		mandatory
		DESCRIPTION
			"This is the data encoding used on the MX25 link.

			nrz  - Non Return to Zero
			nrzi - Non Return to Zero Inverted"
		DEFVAL { nrz }
		::= { cdx6500PPCTMX25SPortEntry 23 }
			
	cdx6500mx25spUpperQueue OBJECT-TYPE
		SYNTAX		INTEGER (5..15)
		ACCESS		read-only
		STATUS		mandatory
		DESCRIPTION
			"This is the maximum number of data packets a channel on this port will
			queue for transmission before invoking flow control to the attached
			channel"
		DEFVAL { 5 }
		::= { cdx6500PPCTMX25SPortEntry 24 }

	cdx6500mx25spLowerQueue OBJECT-TYPE
		SYNTAX		INTEGER (0..4)
		ACCESS		read-only
		STATUS		mandatory
		DESCRIPTION
			"This is the number of data packets a channel on this port will
			have queued for transmission when it releases flow control to the
			attached channel"
		DEFVAL { 0 }
		::= { cdx6500PPCTMX25SPortEntry 25 }




	-- The MX25 Port Statistics Table
	-- This table contains Statistics paramaters 
	-- for the MX25 Port table.
			
	cdx6500PPSTMX25PortTable OBJECT-TYPE
		SYNTAX		SEQUENCE OF Cdx6500PPSTMX25PortEntry
		ACCESS		not-accessible
		STATUS		mandatory
		DESCRIPTION
			"All of the statistics parameters relevant
			 to the MX25 Port table."
		::= { cdx6500PSTPortProtocolGroup 4 }
			
	cdx6500PPSTMX25PortEntry OBJECT-TYPE
		SYNTAX		Cdx6500PPSTMX25PortEntry
		ACCESS		not-accessible
		STATUS		mandatory
		DESCRIPTION
			"A row of MX25 Port statistics parameters."
		INDEX	{ cdx6500mx25pStatsPortNum }
		::= { cdx6500PPSTMX25PortTable 1 }
			
	Cdx6500PPSTMX25PortEntry ::=
		SEQUENCE {
			cdx6500mx25pStatsPortNum
				INTEGER,
			cdx6500mx25pPortStatus
				DisplayString,
			cdx6500mx25pPortSpeed
				INTEGER,
			cdx6500mx25pCharInTotal
				Counter,
			cdx6500mx25pCharOutTotal
				Counter,
			cdx6500mx25pCharsInPerSec
				INTEGER,
			cdx6500mx25pCharsOutPerSec
				INTEGER,
			cdx6500mx25pFrameInTotal
				Counter,
			cdx6500mx25pFrameOutTotal
				Counter,
			cdx6500mx25pFramesInPerSec
				INTEGER,
			cdx6500mx25pFramesOutPerSec
				INTEGER
			}
			
	cdx6500mx25pStatsPortNum OBJECT-TYPE
		SYNTAX		INTEGER (1..54)
		ACCESS		read-only
		STATUS		mandatory
		DESCRIPTION
			"Number of the port"
		::= { cdx6500PPSTMX25PortEntry 1 }
			
	cdx6500mx25pPortStatus OBJECT-TYPE
		SYNTAX		DisplayString (SIZE(2..8))
		ACCESS		read-only
		STATUS		mandatory
		DESCRIPTION
			"Status of the port:

			Up: Port is active
			Down: Port is inactive"
		::= { cdx6500PPSTMX25PortEntry 2 }
			
	cdx6500mx25pPortSpeed OBJECT-TYPE
		SYNTAX		INTEGER
		ACCESS		read-only
		STATUS		mandatory
		DESCRIPTION
			"This is the speed of the port when Clock=Int; this is the
			detected clock speed if Clock=Ext. If Port Speed is 0,
			Clock=Ext but clocking is not being received from attached device."
		::= { cdx6500PPSTMX25PortEntry 3 }
			
	cdx6500mx25pCharInTotal OBJECT-TYPE
		SYNTAX		Counter
		ACCESS		read-only
		STATUS		mandatory
		DESCRIPTION
			"Number of characters received by the port since the last node,
			port, or statistics reset"
		::= { cdx6500PPSTMX25PortEntry 4 }
			
	cdx6500mx25pCharOutTotal OBJECT-TYPE
		SYNTAX		Counter
		ACCESS		read-only
		STATUS		mandatory
		DESCRIPTION
			"Number of characters sent by the port since the last node,
			port, or statistics reset"
		::= { cdx6500PPSTMX25PortEntry 5 }
			
	cdx6500mx25pCharsInPerSec OBJECT-TYPE
		SYNTAX		INTEGER
		ACCESS		read-only
		STATUS		mandatory
		DESCRIPTION
			"Summary of the characters being received over the port"
		::= { cdx6500PPSTMX25PortEntry 6 }
			
	cdx6500mx25pCharsOutPerSec OBJECT-TYPE
		SYNTAX		INTEGER
		ACCESS		read-only
		STATUS		mandatory
		DESCRIPTION
			"Summary of the characters being sent over the port"
		::= { cdx6500PPSTMX25PortEntry 7 }
			
	cdx6500mx25pFrameInTotal OBJECT-TYPE
		SYNTAX		Counter
		ACCESS		read-only
		STATUS		mandatory
		DESCRIPTION
			"Number of frames received by the port since the last node,
			port, or statistics reset"
		::= { cdx6500PPSTMX25PortEntry 8 }
			
	cdx6500mx25pFrameOutTotal OBJECT-TYPE
		SYNTAX		Counter
		ACCESS		read-only
		STATUS		mandatory
		DESCRIPTION
			"Number of frames sent by the port since the last node,
			port, or statistics reset"
		::= { cdx6500PPSTMX25PortEntry 9 }
			
	cdx6500mx25pFramesInPerSec OBJECT-TYPE
		SYNTAX		INTEGER
		ACCESS		read-only
		STATUS		mandatory
		DESCRIPTION
			"Summary of the frames being received over the port"
		::= { cdx6500PPSTMX25PortEntry 10 }
			
	cdx6500mx25pFramesOutPerSec OBJECT-TYPE
		SYNTAX		INTEGER
		ACCESS		read-only
		STATUS		mandatory
		DESCRIPTION
			"Summary of the frames being sent over the port"
		::= { cdx6500PPSTMX25PortEntry 11 }




	-- The MX25 Station Configuration Table
	-- This table contains Configuration paramaters 
	-- for the MX25 Station table.
			
	cdx6500SPCTMX25StationTable OBJECT-TYPE
		SYNTAX		SEQUENCE OF Cdx6500SPCTMX25StationEntry
		ACCESS		not-accessible
		STATUS		mandatory
		DESCRIPTION
			"All of the configuration parameters relevant
			 to the MX.25 station table."
		::= { cdx6500PCTStationProtocolGroup 1 }
			
	cdx6500SPCTMX25StationEntry OBJECT-TYPE
		SYNTAX		Cdx6500SPCTMX25StationEntry
		ACCESS		not-accessible
		STATUS		mandatory
		DESCRIPTION
			"A row of MX.25 station configuration parameters."
		INDEX	{ cdx6500mx25sCfgPortNum, cdx6500mx25sCfgStationNum }
		::= { cdx6500SPCTMX25StationTable 1 }
			
	Cdx6500SPCTMX25StationEntry ::=
		SEQUENCE {
			cdx6500mx25sCfgPortNum
				INTEGER,
			cdx6500mx25sCfgStationNum
				INTEGER,
			cdx6500mx25sStationAddress
				DisplayString,
			cdx6500mx25sPVCChannels
				INTEGER,
			cdx6500mx25sStartingPVC
				INTEGER,
			cdx6500mx25sSVCChannels
				INTEGER,
			cdx6500mx25sStartingSVC
				INTEGER,
			cdx6500mx25sFrameWinSize
				INTEGER,
			cdx6500mx25sPacketWinSize
				INTEGER,
			cdx6500mx25sMX25Options
				DisplayString,
			cdx6500mx25sRCDestination
				DisplayString,
			cdx6500mx25sCUG
				DisplayString,
			cdx6500mx25sBillingRecords
				INTEGER,
			cdx6500mx25sUpperQueue
				INTEGER,
			cdx6500mx25sLowerQueue
				INTEGER
			}
			
	cdx6500mx25sCfgPortNum OBJECT-TYPE
		SYNTAX		INTEGER (1..54)
		ACCESS		read-only
		STATUS		mandatory
		DESCRIPTION
			"MX25 Port Number"
		DEFVAL { 1 }
		::= { cdx6500SPCTMX25StationEntry 1 }
			
	cdx6500mx25sCfgStationNum OBJECT-TYPE
		SYNTAX		INTEGER (1..4)
		ACCESS		read-only
		STATUS		mandatory
		DESCRIPTION
			"The number of the controller on the multidrop line.  Also used for
			routing purposes."
		DEFVAL { 1 }
		::= { cdx6500SPCTMX25StationEntry 2 }
			
	cdx6500mx25sStationAddress OBJECT-TYPE
		SYNTAX		DisplayString (SIZE(0..2))
		ACCESS		read-only
		STATUS		mandatory
		DESCRIPTION
			"The station address on the multidrop line."
		DEFVAL { 04 }
		::= { cdx6500SPCTMX25StationEntry 3 }
			
	cdx6500mx25sPVCChannels OBJECT-TYPE
		SYNTAX		INTEGER (0..128)
		ACCESS		read-only
		STATUS		mandatory
		DESCRIPTION
			"Number of logical channels used for Permanent Virtual Circuits.
			The total number of PVC and SVC channels on a link should be kept as
			small as possible and consistent with needs.
			PVC connections must be configured in the PVC Table."
		DEFVAL { 0 }
		::= { cdx6500SPCTMX25StationEntry 4 }
			
	cdx6500mx25sStartingPVC OBJECT-TYPE
		SYNTAX		INTEGER (1..255)
		ACCESS		read-only
		STATUS		mandatory
		DESCRIPTION
			"This is the starting logical channel number for the Permanent Virtual
			Circuits on this link. Not used if the number of PVCs = 0."
		DEFVAL { 1 }
		::= { cdx6500SPCTMX25StationEntry 5 }
			
	cdx6500mx25sSVCChannels OBJECT-TYPE
		SYNTAX		INTEGER (0..255)
		ACCESS		read-only
		STATUS		mandatory
		DESCRIPTION
			"Number of logical channels used in Switched Virtual Circuits.
			The total number of PVC and SVC channels on a link should be kept as
			small as possible and consistent with needs."
		DEFVAL { 16 }
		::= { cdx6500SPCTMX25StationEntry 6 }
			
	cdx6500mx25sStartingSVC OBJECT-TYPE
		SYNTAX		INTEGER (0..255)
		ACCESS		read-only
		STATUS		mandatory
		DESCRIPTION
			"This is the starting logical channel number for the Switched Virtual
			Circuits on this link. Not used if the number of SVCs = 0."
		DEFVAL { 1 }
		::= { cdx6500SPCTMX25StationEntry 7 }
			
	cdx6500mx25sFrameWinSize OBJECT-TYPE
		SYNTAX		INTEGER (1..7)
		ACCESS		read-only
		STATUS		mandatory
		DESCRIPTION
			"Frame level window size must be set to the same value in
			devices at each end of the link."
		DEFVAL { 7 }
		::= { cdx6500SPCTMX25StationEntry 8 }
			
	cdx6500mx25sPacketWinSize OBJECT-TYPE
		SYNTAX		INTEGER (1..7)
		ACCESS		read-only
		STATUS		mandatory
		DESCRIPTION
			"Packet level window size must be set to the same value in
			devices at each end of the link."
		DEFVAL { 2 }
		::= { cdx6500SPCTMX25StationEntry 9 }
			
	cdx6500mx25sMX25Options OBJECT-TYPE
		SYNTAX		DisplayString (SIZE(3..22))
		ACCESS		read-only
		STATUS		mandatory
		DESCRIPTION
			"Select options on this MX.25 port as follows:

			NONE - no option specified
			HOLD - hold calls over link restart
			CUG  - check closed user group; otherwise, CUG passes transparently
			INL  - inter-node link. Link goes to another 6500 device
			INLA - set with INL option when an MX.25 link connection is to
			       a 6500 node using 2.12.04 or earlier

			Any combination of the above specified by summing
			(e.g. HOLD+CUG+. . .)."
		DEFVAL { "NONE" }
		::= { cdx6500SPCTMX25StationEntry 10 }
			
	cdx6500mx25sRCDestination OBJECT-TYPE
		SYNTAX		DisplayString (SIZE(0..32))
		ACCESS		read-only
		STATUS		mandatory
		DESCRIPTION
			"All calls entering this port will be routed to the destination
			specified in this parameter, irrespective of route selection table
			entries. For example, to route calls to port 1, use P1.
			To route calls to port 2, station 4, use P2S4.
			Blank this field to disable this function."
		DEFVAL { '20'H } -- blank
		::= { cdx6500SPCTMX25StationEntry 11 }
			
	cdx6500mx25sCUG OBJECT-TYPE
		SYNTAX		DisplayString (SIZE(0..23))
		ACCESS		read-only
		STATUS		mandatory
		DESCRIPTION
			"The port may be a member of up to 8 different Closed User
			Groups (CUGs). Each CUG membership must be a two digit number
			(except --) and separated by a comma. ( e.g. 12,34,56,09,02,03 ).

			--    - No CUG Membership
			00-99 - CUG Membership"
		::= { cdx6500SPCTMX25StationEntry 12 }
			
	cdx6500mx25sBillingRecords OBJECT-TYPE
		SYNTAX		INTEGER {
					off(0),
					on(1)
					}
		ACCESS		read-only
		STATUS		mandatory
		DESCRIPTION
			"This controls whether billing (accounting) records will be created for
			calls on this port."
		DEFVAL { off }
		::= { cdx6500SPCTMX25StationEntry 13 }
			
	cdx6500mx25sUpperQueue OBJECT-TYPE
		SYNTAX		INTEGER (5..15)
		ACCESS		read-only
		STATUS		mandatory
		DESCRIPTION
			"This is the maximum number of data packets a channel on this port will
			queue for transmission before invoking flow control to the attached
			channel"
		DEFVAL { 5 }
		::= { cdx6500SPCTMX25StationEntry 14 }
			
	cdx6500mx25sLowerQueue OBJECT-TYPE
		SYNTAX		INTEGER (0..4)
		ACCESS		read-only
		STATUS		mandatory
		DESCRIPTION
			"This is the number of data packets a channel on this port will
			have queued for transmission when it releases flow control to the
			attached channel"
		DEFVAL { 0 }
		::= { cdx6500SPCTMX25StationEntry 15 }




	-- The MX25 Station Statistics Table
	-- This table contains Statistics paramaters 
	-- for the MX25 Station table.
			
	cdx6500SPSTMX25StationTable OBJECT-TYPE
		SYNTAX		SEQUENCE OF Cdx6500SPSTMX25StationEntry
		ACCESS		not-accessible
		STATUS		mandatory
		DESCRIPTION
			"All of the statistics parameters relevant
			 to the MX25 Station table."
		::= { cdx6500PSTStationProtocolGroup 1 }
			
	cdx6500SPSTMX25StationEntry OBJECT-TYPE
		SYNTAX		Cdx6500SPSTMX25StationEntry
		ACCESS		not-accessible
		STATUS		mandatory
		DESCRIPTION
			"A row of MX25 Station statistics parameters."
		INDEX	{ cdx6500mx25sStatsPortNum, cdx6500mx25sStatsStationNum }
		::= { cdx6500SPSTMX25StationTable 1 }
			
	Cdx6500SPSTMX25StationEntry ::=
		SEQUENCE {
			cdx6500mx25sStatsPortNum
				INTEGER,
			cdx6500mx25sStatsStationNum
				INTEGER,
			cdx6500mx25sStatsStnAddr
				DisplayString,
			cdx6500mx25sCharInTotal
				Counter,
			cdx6500mx25sCharOutTotal
				Counter,
			cdx6500mx25sCharsInPerSec
				INTEGER,
			cdx6500mx25sCharsOutPerSec
				INTEGER,
			cdx6500mx25sFrameInTotal
				Counter,
			cdx6500mx25sFrameOutTotal
				Counter,
			cdx6500mx25sFramesInPerSec
				INTEGER,
			cdx6500mx25sFramesOutPerSec
				INTEGER,
			cdx6500mx25sCallCount
				INTEGER
			}
			
	cdx6500mx25sStatsPortNum OBJECT-TYPE
		SYNTAX		INTEGER (1..54)
		ACCESS		read-only
		STATUS		mandatory
		DESCRIPTION
			"Number of the port"
		::= { cdx6500SPSTMX25StationEntry 1 }
			
	cdx6500mx25sStatsStationNum OBJECT-TYPE
		SYNTAX		INTEGER (1..4)
		ACCESS		read-only
		STATUS		mandatory
		DESCRIPTION
			"Station reference number."
		::= { cdx6500SPSTMX25StationEntry 2 }
			
	cdx6500mx25sStatsStnAddr OBJECT-TYPE
		SYNTAX		DisplayString (SIZE(0..2))
		ACCESS		read-only
		STATUS		mandatory
		DESCRIPTION
			"Configured station address."
		::= { cdx6500SPSTMX25StationEntry 3 }
			
	cdx6500mx25sCharInTotal OBJECT-TYPE
		SYNTAX		Counter
		ACCESS		read-only
		STATUS		mandatory
		DESCRIPTION
			"Number of characters received by the port since the last node,
			port, or statistics reset"
		::= { cdx6500SPSTMX25StationEntry 4 }
			
	cdx6500mx25sCharOutTotal OBJECT-TYPE
		SYNTAX		Counter
		ACCESS		read-only
		STATUS		mandatory
		DESCRIPTION
			"Number of characters sent by the port since the last node,
			port, or statistics reset"
		::= { cdx6500SPSTMX25StationEntry 5 }
			
	cdx6500mx25sCharsInPerSec OBJECT-TYPE
		SYNTAX		INTEGER
		ACCESS		read-only
		STATUS		mandatory
		DESCRIPTION
			"Summary of the characters being received over the port"
		::= { cdx6500SPSTMX25StationEntry 6 }
			
	cdx6500mx25sCharsOutPerSec OBJECT-TYPE
		SYNTAX		INTEGER
		ACCESS		read-only
		STATUS		mandatory
		DESCRIPTION
			"Summary of the characters being sent over the port"
		::= { cdx6500SPSTMX25StationEntry 7 }
			
	cdx6500mx25sFrameInTotal OBJECT-TYPE
		SYNTAX		Counter
		ACCESS		read-only
		STATUS		mandatory
		DESCRIPTION
			"Number of frames received by the port since the last node,
			port, or statistics reset"
		::= { cdx6500SPSTMX25StationEntry 8 }
			
	cdx6500mx25sFrameOutTotal OBJECT-TYPE
		SYNTAX		Counter
		ACCESS		read-only
		STATUS		mandatory
		DESCRIPTION
			"Number of frames sent by the port since the last node,
			port, or statistics reset"
		::= { cdx6500SPSTMX25StationEntry 9 }
			
	cdx6500mx25sFramesInPerSec OBJECT-TYPE
		SYNTAX		INTEGER
		ACCESS		read-only
		STATUS		mandatory
		DESCRIPTION
			"Summary of the frames being received over the port"
		::= { cdx6500SPSTMX25StationEntry 10 }
			
	cdx6500mx25sFramesOutPerSec OBJECT-TYPE
		SYNTAX		INTEGER
		ACCESS		read-only
		STATUS		mandatory
		DESCRIPTION
			"Summary of the frames being sent over the port"
		::= { cdx6500SPSTMX25StationEntry 11 }
			
	cdx6500mx25sCallCount OBJECT-TYPE
		SYNTAX		INTEGER
		ACCESS		read-only
		STATUS		mandatory
		DESCRIPTION
			"Current number of calls"
		::= { cdx6500SPSTMX25StationEntry 12 }


	-- The MX25 Station Controls Table
	-- This table contains Control paramaters 
	-- for the MX25 Station table.
			
	cdx6500ContMX25StationTable OBJECT-TYPE
		SYNTAX		SEQUENCE OF Cdx6500ContMX25StationEntry
		ACCESS		not-accessible
		STATUS		mandatory
		DESCRIPTION
			"All of the control parameters relevant
			 to the MX25 Station table."
		::= { cdx6500ContMX25 1 }
			
	cdx6500ContMX25StationEntry OBJECT-TYPE
		SYNTAX		Cdx6500ContMX25StationEntry
		ACCESS		not-accessible
		STATUS		mandatory
		DESCRIPTION
			"A row of MX25 Station Control parameters."
		INDEX	{ cdx6500mx25sContPortNum, cdx6500mx25sContStationNum }
		::= { cdx6500ContMX25StationTable 1 }
			
	Cdx6500ContMX25StationEntry ::=
		SEQUENCE {
			cdx6500mx25sContPortNum
				INTEGER,
			cdx6500mx25sContStationNum
				INTEGER,
			cdx6500mx25sContBootStation
				INTEGER,
			cdx6500mx25sContDisableStation
				INTEGER,
			cdx6500mx25sContEnableStation
				INTEGER,
			cdx6500mx25sContBusyOutStation
				INTEGER,
			cdx6500mx25sContResetStnStats
				INTEGER
			}
			
	cdx6500mx25sContPortNum OBJECT-TYPE
		SYNTAX		INTEGER (1..54)
		ACCESS		not-accessible
		STATUS		mandatory
		DESCRIPTION
			"MX25 Port Number"
		::= { cdx6500ContMX25StationEntry 1 }
			
	cdx6500mx25sContStationNum OBJECT-TYPE
		SYNTAX		INTEGER (1..4)
		ACCESS		not-accessible
		STATUS		mandatory
		DESCRIPTION
			"MX25 Station Number"
		::= { cdx6500ContMX25StationEntry 2 }
			
	cdx6500mx25sContBootStation OBJECT-TYPE
		SYNTAX		INTEGER {
					boot(1),
					noBoot(2)
					}
		ACCESS		write-only
		STATUS		mandatory
		DESCRIPTION
			"Boots the specified MX25 station.

			1 - Boot Station
			2 - Do not boot Station"
		DEFVAL { noBoot }
		::= { cdx6500ContMX25StationEntry 3 }
			
	cdx6500mx25sContDisableStation OBJECT-TYPE
		SYNTAX		INTEGER {
					disable(1),
					noDisable(2)
					}
		ACCESS		write-only
		STATUS		mandatory
		DESCRIPTION
			"Disables the specified MX25 station.

			1 - Disable Station
			2 - Do not disable Station"
		DEFVAL { noDisable }
		::= { cdx6500ContMX25StationEntry 4 }
			
	cdx6500mx25sContEnableStation OBJECT-TYPE
		SYNTAX		INTEGER {
					enable(1),
					noEnable(2)
					}
		ACCESS		write-only
		STATUS		mandatory
		DESCRIPTION
			"Enables the specified MX25 station.

			1 - Enable Station
			2 - Do not enable Station"
		DEFVAL { noEnable }
		::= { cdx6500ContMX25StationEntry 5 }
			
	cdx6500mx25sContBusyOutStation OBJECT-TYPE
		SYNTAX		INTEGER {
					busyOut(1),
					noBusyOut(2)
					}
		ACCESS		write-only
		STATUS		mandatory
		DESCRIPTION
			"Busy outs the specified MX25 station.

			1 - Busyout Station
			2 - Do not busyout Station"
		DEFVAL { noBusyOut }
		::= { cdx6500ContMX25StationEntry 6 }

	cdx6500mx25sContResetStnStats OBJECT-TYPE
		SYNTAX		INTEGER {
					reset(1),
					noReset(2)
					}
		ACCESS		write-only
		STATUS		mandatory
		DESCRIPTION
			"Busy outs the specified MX25 station.

			1 - Reset Station Statistics
			2 - Do not reset Station Statistics"
		DEFVAL { noReset }
		::= { cdx6500ContMX25StationEntry 7 }

END
