SYNOPTICS-TOKENRING-MIB

-- Token Ring MIB 3.1
-- DRAFT Revision 10/25/91
-- Printed 10/29/91

-- Copyright 1991 SynOptics Communications, Inc.  All Rights
-- Reserved.  Reproduction of this document is authorized on
-- condition that the foregoing copyright notice is included.
-- This SynOptics SNMP Management Information Base Specification
-- (Specification) embodies SynOptics' confidential and
-- proprietary intellectual property.  SynOptics retains all
-- title and ownership in the Specification, including any
-- revisions.  
--
-- It is SynOptics intent to encourage the widespread use of
-- this Specification in connection with the management of
-- SynOptics products. SynOptics grants vendors, end-users,
-- and other interested parties a non-exclusive license to
-- use this Specification in connection with the management
-- of SynOptics products.
--
-- This Specification is supplied "AS IS," and SynOptics makes
-- no warranty, either express or implied, as to the use,
-- operation, condition, or performance of the Specification.


DEFINITIONS ::= BEGIN


-- SECTION 1: Top Level Definitions

-- Imports

IMPORTS
	Counter, TimeTicks	FROM RFC1155-SMI
	OBJECT-TYPE		FROM RFC-1212
	s3000TokenRing		FROM SYNOPTICS-COMMON-MIB;


-- Groups

s3000TrBoard		OBJECT IDENTIFIER ::= { s3000TokenRing 2 }
s3000TrPort		OBJECT IDENTIFIER ::= { s3000TokenRing 3 }
s3000TrNmm		OBJECT IDENTIFIER ::= { s3000TokenRing 4 }
s3000TrNode		OBJECT IDENTIFIER ::= { s3000TokenRing 5 }
s3000TrRing		OBJECT IDENTIFIER ::= { s3000TokenRing 7 }
s3TrRingStats		OBJECT IDENTIFIER ::= { s3000TrRing 1 }


-- SECTION 2: Token Ring Board Group


-- Common Board Table

s3TrCommonBoardTable OBJECT-TYPE
	SYNTAX	SEQUENCE OF S3TrCommonBoardEntry
	ACCESS	not-accessible
	STATUS	mandatory
	DESCRIPTION
		"Information maintained for each token ring board.  The 
		information can be retrieved for any token ring board, even if
 		the board is not on the same backplane ring as this NMM. The 
		instance is the slot number of the concentrator that the board 
		occupies."
	::= { s3000TrBoard 2 }

s3TrCommonBoardEntry OBJECT-TYPE
	SYNTAX	S3TrCommonBoardEntry
	ACCESS	not-accessible
	STATUS	mandatory
	DESCRIPTION
		"There is one entry per board in this table."
	INDEX	{ s3TrCommonBoardIndex }
	::= { s3TrCommonBoardTable 1 }

S3TrCommonBoardEntry ::= SEQUENCE {
	s3TrCommonBoardIndex
		INTEGER,
	s3TrCommonBoardRing1or2
		INTEGER,
	s3TrCommonBoardRingSpeed
		INTEGER
}
		
s3TrCommonBoardIndex OBJECT-TYPE
	SYNTAX	INTEGER
	ACCESS	read-only
	STATUS	mandatory
	DESCRIPTION
		"A unique value for each board.  Its value ranges between 1 
		and 12. The value for each board must remain constant at 
		least from one re-initialization of the entity's network 
		management system to the next re-initialization. If a board is
 		inserted or reinserted in a concentrator then the NMM has to 
		be reinitialized."
	::= { s3TrCommonBoardEntry 1 }

s3TrCommonBoardRing1or2 OBJECT-TYPE
	SYNTAX	INTEGER {
		other(1),	-- not a valid ring number
		ring1(2),	-- use/using ring 1 on the concentrator
		ring2(3)	-- use/using ring 2 on the concentrator
	}	
	ACCESS	read-only
	STATUS	mandatory
	DESCRIPTION
		"Determines which ring the board is currently using on the 
		concentrator backplane."
	::=  { s3TrCommonBoardEntry 2 }

s3TrCommonBoardRingSpeed OBJECT-TYPE
	SYNTAX	INTEGER {
		other(1),	-- unknown speed
		speed1M(2),	-- 1 Mbps for standard compatibility
		speed4M(3),	-- 4 Mbps
		speed16M(4)	-- 16 Mbps
	}	
	ACCESS	read-only
	STATUS	mandatory
	DESCRIPTION
		"Token Ring speed of the ring that this board is connected to."
	::=  { s3TrCommonBoardEntry 3 }



-- SECTION 3: Token Ring Port Group


-- Port Table

s3TrPortTable OBJECT-TYPE
	SYNTAX	SEQUENCE OF S3TrPortEntry
	ACCESS	not-accessible
	STATUS	mandatory
	DESCRIPTION
		"A table containing information about each port of a LattisNet 
		concentrator.  The number of entries is given by knowing the 
		number of occupied slots in s3ChassisSlotConfigTable whose 
		s3SlotModuleType is of a token ring type and is on the same 
		physical ring as the agent NMM."
	::= { s3000TrPort 1 }

s3TrPortEntry OBJECT-TYPE
	SYNTAX	S3TrPortEntry
	ACCESS	not-accessible
	STATUS	mandatory
	DESCRIPTION
		"A port entry containing objects at the port level for a 
		particular port."
	INDEX	{ s3TrPortBoardIndex, s3TrPortIndex }
	::= { s3TrPortTable 1 }

S3TrPortEntry ::= SEQUENCE {
	s3TrPortBoardIndex
		INTEGER,
	s3TrPortIndex
		INTEGER,
	s3TrPortWrap
		INTEGER,
	s3TrPortTestLatch
		INTEGER,
	s3TrPortRelayStatus
		INTEGER,
	s3TrPortPhantomStatus
		INTEGER,
	s3TrPortPhantomChangeFlag
		INTEGER,
	s3TrPortChgSyn2IBM
		INTEGER,
	s3TrPortStrap
		INTEGER
}

s3TrPortBoardIndex OBJECT-TYPE
	SYNTAX	INTEGER
	ACCESS	read-only
	STATUS	mandatory
	DESCRIPTION
		"A unique value for each board.  Its value ranges between 1 
		and 12. The value for each board must remain constant at 
		least from one re-initialization of the entity's network 
		management system to the next re-initialization. If a board 
		is inserted or reinserted in a concentrator then the NMM has 
		to be reinitialized."
	::=  { s3TrPortEntry 1 }

s3TrPortIndex OBJECT-TYPE
	SYNTAX	INTEGER
	ACCESS	read-only
	STATUS	mandatory
	DESCRIPTION
		"A unique value for each port.  Its value ranges between 1 
		and 12. The value for each port must remain constant at least 
		from one re-initialization of the entity's network management 
		system to the next re-initialization.  If the board is an NMM 
		board it will only have 2 ports, with Port 1 being for Ring In
		and Port 2 being for Ring Out."
	::=  { s3TrPortEntry 2 }

s3TrPortWrap OBJECT-TYPE
	SYNTAX	INTEGER {
		other(1),	-- port not wrapped or connected
		wrap(2),
		connect(3)
	}
	ACCESS	read-write
	STATUS	mandatory
	DESCRIPTION
		"Status of the port.  Setting wrap(2) disconnects the port 
		from the ring and setting this object to connect(3) connects 
		the port to the ring."
	::=  { s3TrPortEntry 3 }

s3TrPortTestLatch OBJECT-TYPE
	SYNTAX	INTEGER {
		other(1),	-- not supported
		on(2),		-- test latch activated
		off(3)		-- test latch not activated
	}
	ACCESS	read-write
	STATUS	mandatory
	DESCRIPTION
		"Status of the test latch which is used to set the channel 
		decoder used to monitor the health of the communication path 
		between the NMM and the module channel."
	::=  { s3TrPortEntry 4 }

s3TrPortRelayStatus OBJECT-TYPE
	SYNTAX	INTEGER {
		other(1),	-- not supported
		on(2),		-- channel is part of the ring
		off(3)		-- channel is bypassed
	}
	ACCESS	read-only
	STATUS	mandatory
	DESCRIPTION
		"Status of the channel's present relay mode.  On(2) means the 
		channel is in the ring and off(3) means the channel is 
		bypassed."
	::=  { s3TrPortEntry 5 }

s3TrPortPhantomStatus OBJECT-TYPE
	SYNTAX	INTEGER {
		other(1),
		on(2),
		off(3)
	}
	ACCESS	read-only
	STATUS	mandatory
	DESCRIPTION
		"Status of the ring access request signal."
	::=  { s3TrPortEntry 6 }

s3TrPortPhantomChangeFlag OBJECT-TYPE
	SYNTAX	INTEGER {
		other(1),
		noChange(2),
		change(3)
	}
	ACCESS	read-only
	STATUS	mandatory
	DESCRIPTION
		"Change(3) indicates that port phantom has been changed from 
		OFF to ON.  After inquiry by NMS, it will be cleared to 
		noChange(2).  Port phantom changing from ON to OFF has no 
		impact on this object."
	::=  { s3TrPortEntry 7 }

s3TrPortChgSyn2IBM OBJECT-TYPE
	SYNTAX	INTEGER {
		notSupported(1),
		synoptics(2),
		ibm(3)
	}
	ACCESS	read-write
	STATUS	mandatory
	DESCRIPTION
		"If the port is on a ring in/ring out module this object 
		changes the strap state depending on the jumper setting 
		retrieved as s3TrPortStrap.  If the strap is set for SynOptics
 		phantom option, this object can be changed to ibm(3).  If the 
		strap is set for non-SynOptics option, this object can not be 
		changed. Non ring in/ring out modules or fiber ring in/ring out
		modules must take on the value of notSupported(1)."
	::=  { s3TrPortEntry 8 }

s3TrPortStrap OBJECT-TYPE
	SYNTAX	INTEGER {
		notSupported(1),
		synoptics(2),
		ibm(3)
	}
	ACCESS	read-only
	STATUS	mandatory
	DESCRIPTION
		"If the port is on a ring in/ring out module this object 
		signifies whether the hardware jumper is in synoptics(2) mode 
		or ibm(3) mode.  This information is retrieved using a  NMI 
		command. For ports on fiber ring in/ring out modules, and 
		those ports not on ring in/ring out modules, the agent always 
		returns notSupported(1)."
	::=  { s3TrPortEntry 9 }


-- SECTION 4: Token Ring NMM Group


s3TrNmmFnNum OBJECT-TYPE
	SYNTAX	INTEGER
	ACCESS	read-write
	STATUS	mandatory
	DESCRIPTION
		"Defines the flat network number that this NMM is part of."
	::=  { s3000TrNmm 1 }

s3TrNmmRingNum OBJECT-TYPE
	SYNTAX	INTEGER
	ACCESS	read-only
	STATUS	mandatory
	DESCRIPTION
		"Defines the segment number that this NMM is connected to."
	::=  { s3000TrNmm 2 }

s3TrNmmSlotNum OBJECT-TYPE
	SYNTAX	INTEGER
	ACCESS	read-only
	STATUS	deprecated
	DESCRIPTION
		"Defines the slot number that this NMM is connected to.  New 
		NMS implementations should use the object s3AgentMySlotId 
		defined in the common MIB."
	::=  { s3000TrNmm 3 }

s3TrNmmFpuIdRev OBJECT-TYPE
	SYNTAX	INTEGER
	ACCESS	read-only
	STATUS	mandatory
	DESCRIPTION
		"The revision of the Front-end Frame Processing unit.  
		0=Rev. A, 1=Rev. B, etc."
	::=  { s3000TrNmm 4 }

s3TrNmmFpuStatus OBJECT-TYPE
	SYNTAX	INTEGER {
		notPresent(1),
		notOperational(2),	-- present, but not operational
		operational(3)		-- present and operational
	}
	ACCESS	read-only
	STATUS	mandatory
	DESCRIPTION
		"The status of the Front-end Frame Processing Unit."
	::=  { s3000TrNmm 5 }

s3TrNmmDramSize OBJECT-TYPE
	SYNTAX	INTEGER{
		other(1),	-- unknown size
		k512(2),	-- 512K memory
		oneMeg(3),
		twoMeg(4)
	}
	ACCESS	read-only
	STATUS	mandatory
	DESCRIPTION
		"The highest address of the DRAM in the NMM memory map."
	::=  { s3000TrNmm 6 }

s3TrNmmEepromSize OBJECT-TYPE
	SYNTAX	INTEGER {
		other(1),	-- unknown size
		k2kby8(2),	-- 2k*8
		k8kby8(3)	-- 8k*8
	}
	ACCESS	read-only
	STATUS	mandatory
	DESCRIPTION
		"The size of the EEPROM in the NMM memory map."
	::=  { s3000TrNmm 7 }

s3TrNmmGrpAddrFrmsRxOk OBJECT-TYPE
	SYNTAX	Counter	
	ACCESS	read-only
	STATUS	mandatory
	DESCRIPTION
		"Number of Group Address frames received without error by this 
		NMM. Note:  The NMM counts only Group Address frames that are 
		addressed to its own Group Address(es)."
	::=  { s3000TrNmm 8 }

s3TrNmmRing1or2 OBJECT-TYPE
	SYNTAX	INTEGER {
		other(1),	-- not a valid ring number
		ring1(2),	-- use/using ring 1 on the concentrator
		ring2(3)	-- use/using ring 2 on the concentrator
	}	
	ACCESS	read-only
	STATUS	mandatory
	DESCRIPTION
		"Determines which ring the NMM is currently using on the 
		concentrator backplane."
	::=  { s3000TrNmm 9 }

s3TrNmmRingSpeed OBJECT-TYPE
	SYNTAX	INTEGER {
		other(1),	-- unknown speed
		speed1M(2),	-- 1 Mbps for standard compatibility
		speed4M(3),	-- 4 Mbps
		speed16M(4)	-- 16 Mbps
	}	
	ACCESS	read-only
	STATUS	mandatory
	DESCRIPTION
		"Token Ring speed."
	::=  { s3000TrNmm 10 }

s3TrNmmHexDisplay OBJECT-TYPE
	SYNTAX	OCTET STRING (SIZE(4))	
	ACCESS	read-only
	STATUS	mandatory
	DESCRIPTION
		"4 octet hex display string that is displayed on the NMM 
		control panel."
	::=  { s3000TrNmm 11 }

s3TrNmmEpromSize OBJECT-TYPE
	SYNTAX	INTEGER {
		other(1),		-- unknown size
		k2kby8(2),		-- 2k*8
		k8kby8(3),		-- 8k*8
		k16kby8(4),		-- 16k*8
		k32kby8(5),		-- 32k*8
		k64kby8(6),		-- 64k*8
		k128kby8(7),		-- 128k*8
		k256kby8(8)		-- 256k*8
	}
	ACCESS	read-only
	STATUS	mandatory
	DESCRIPTION
		"The size of the EPROM in the NMM memory map."
	::=  { s3000TrNmm 12 }



-- SECTION 5: Token Ring Station Group


-- Node table

-- list of all nodes that are active on the local token ring that this 
-- concentrator is connected to.

s3TrNodeTable OBJECT-TYPE
	SYNTAX	SEQUENCE OF S3TrNodeEntry
	ACCESS	not-accessible
	STATUS	mandatory
	DESCRIPTION
		"Table containing station specific information."
	::= { s3000TrNode 1 }

s3TrNodeEntry OBJECT-TYPE
	SYNTAX	S3TrNodeEntry
	ACCESS	not-accessible
	STATUS	mandatory
	DESCRIPTION
		"Entry in the table containing counters and profiling 
		information for each node detected on the local token ring."
	INDEX	{ s3TrNodeEntMacAddress }
	::= { s3TrNodeTable 1 }

S3TrNodeEntry ::= SEQUENCE {
	s3TrNodeEntMacAddress
		OCTET STRING,
	s3TrNodeEntStatus
		INTEGER,
	s3TrNodeEntNodeStatus
		OCTET STRING,
	s3TrNodeLineErrs
		Counter,
	s3TrNodeBurstErrs
		Counter,
	s3TrNodeAriFciErrs
		Counter,
	s3TrNodeLostFrames
		Counter,
	s3TrNodeRcvCongestErrs
		Counter,
	s3TrNodeFrmCopyErrs
		Counter,
	s3TrNodeTokenErrs
		Counter,
	s3TrNodeInternalErrs
		Counter,
	s3TrNodeAbortTransErrs
		Counter,
	s3TrNodeFrequencyErrs
		Counter,
	s3TrNodeEntProductId
		OCTET STRING,
	s3TrNodeEntUna
		OCTET STRING,
	s3TrNodeEntNodeVersion
		OCTET STRING,
	s3TrNodeEntPhysDrop
		OCTET STRING,
	s3TrNodeEntFuncAddr
		OCTET STRING,
	s3TrNodeEntAuthFuncClass
		OCTET STRING,
	s3TrNodeEntAuthAccPriority
		OCTET STRING,
	s3TrNodeEntGrpAddr
		OCTET STRING,
	s3TrNodeEntStationId
		OCTET STRING,
	s3TrNodeEntBeaconType
		INTEGER,
	s3TrNodeBeaconCnt
		Counter,
	s3TrNodeLastBeaconTime
		TimeTicks,
	s3TrNodeLastInsertTime
		TimeTicks,
	s3TrNodeFirstInsertTime
		TimeTicks,
	s3TrNodeLastDeinsertTime
		TimeTicks,
	s3TrNodeRemoveStation
		INTEGER
}

s3TrNodeEntMacAddress OBJECT-TYPE
	SYNTAX	OCTET STRING (SIZE(6))
	ACCESS	read-only
	STATUS	mandatory
	DESCRIPTION
		"MAC address of node that this entry in the table is for."
	::=  { s3TrNodeEntry 1 }

s3TrNodeEntStatus OBJECT-TYPE
	SYNTAX	INTEGER {
		beaconing(1),
		notBeaconing(2)
	}
	ACCESS	read-only
	STATUS	mandatory
	DESCRIPTION
		"Tells whether the station is currently beaconing or not."
	::=  { s3TrNodeEntry 4 }

s3TrNodeEntNodeStatus OBJECT-TYPE
	SYNTAX	OCTET STRING (SIZE(6))
	ACCESS	read-only
	STATUS	mandatory
	DESCRIPTION
		"Node status as defined in 802.5 specification 
		(section 3.3.2.18)."
	::=  { s3TrNodeEntry 5 }

s3TrNodeLineErrs OBJECT-TYPE
	SYNTAX	Counter
	ACCESS	read-only
	STATUS	mandatory
	DESCRIPTION
		"Number of line errors.  Section 3.8.1 of IEEE 802.5 
		specification."
	::=  { s3TrNodeEntry 6 }

s3TrNodeBurstErrs OBJECT-TYPE
	SYNTAX	Counter
	ACCESS	read-only
	STATUS	mandatory
	DESCRIPTION
		"Number of burst errors.  Section 3.8.3 of IEEE 802.5 
		specification."
	::=  { s3TrNodeEntry 7 }

s3TrNodeAriFciErrs OBJECT-TYPE
	SYNTAX	Counter
	ACCESS	read-only
	STATUS	mandatory
	DESCRIPTION
		"Number of ARI FCI errors.  See AC errors, Section 3.8.4 of 
		IEEE 802.5 specification."
	::=  { s3TrNodeEntry 8 }

s3TrNodeLostFrames OBJECT-TYPE
	SYNTAX	Counter
	ACCESS	read-only
	STATUS	mandatory
	DESCRIPTION
		"Number of frames lost.  Section 3.8.6 of IEEE 802.5 
		specification."
	::=  { s3TrNodeEntry 9 }

s3TrNodeRcvCongestErrs OBJECT-TYPE
	SYNTAX	Counter
	ACCESS	read-only
	STATUS	mandatory
	DESCRIPTION
		"Number of receive congestion errors.  Section 3.8.7 of IEEE 
		802.5 specification."
	::=  { s3TrNodeEntry 10 }

s3TrNodeFrmCopyErrs OBJECT-TYPE
	SYNTAX	Counter
	ACCESS	read-only
	STATUS	mandatory
	DESCRIPTION
		"Number of frame copy errors.  Section 3.8.8 of IEEE 802.5 
		specification."
	::=  { s3TrNodeEntry 11 }

s3TrNodeTokenErrs OBJECT-TYPE
	SYNTAX	Counter
	ACCESS	read-only
	STATUS	mandatory
	DESCRIPTION
		"Number of token errors.  Section 3.8.10 of IEEE 802.5 specification."
	::=  { s3TrNodeEntry 12 }

s3TrNodeInternalErrs OBJECT-TYPE
	SYNTAX	Counter
	ACCESS	read-only
	STATUS	mandatory
	DESCRIPTION
		"Number of internal errors.  Section 3.8.2 of IEEE 802.5 
		specification."
	::=  { s3TrNodeEntry 13 }

s3TrNodeAbortTransErrs OBJECT-TYPE
	SYNTAX	Counter
	ACCESS	read-only
	STATUS	mandatory
	DESCRIPTION
		"Number of abort delimiter transmitted errors.  Section 3.8.5 
		of IEEE 802.5 specification."
	::=  { s3TrNodeEntry 14 }

s3TrNodeFrequencyErrs OBJECT-TYPE
	SYNTAX	Counter
	ACCESS	read-only
	STATUS	mandatory
	DESCRIPTION
		"Number of frequency errors. Section 3.8.9 of IEEE 802.5 
		specification."
	::=  { s3TrNodeEntry 15 }

s3TrNodeEntProductId OBJECT-TYPE
	SYNTAX	OCTET STRING (SIZE(18))
	ACCESS	read-only
	STATUS	mandatory
	DESCRIPTION
		"A brief string describing the product specified by the vendor.
		Section 3.3.2.14 of IEEE 802.5 specification. The characters 
		in the string are represented in EBCDIC for IBM products, in 
		ASCII for others."
	::=  { s3TrNodeEntry 16 }

s3TrNodeEntUna OBJECT-TYPE
	SYNTAX	OCTET STRING (SIZE(6))
	ACCESS	read-only
	STATUS	mandatory
	DESCRIPTION
		"The Upstream Neighbor Address.  Section 3.3.2.15 of IEEE 
		802.5 specification."
	::=  { s3TrNodeEntry 17 }

s3TrNodeEntNodeVersion OBJECT-TYPE
	SYNTAX	OCTET STRING (SIZE(10))
	ACCESS	read-only
	STATUS	mandatory
	DESCRIPTION
		"String that represents the version of the station software.  
		Section 3.3.2.17 of IEEE 802.5 specification. The characters 
		in the string are represented in EBCDIC for IBM products, in 
		ASCII for others."
	::=  { s3TrNodeEntry 18 }

s3TrNodeEntPhysDrop OBJECT-TYPE
	SYNTAX	OCTET STRING (SIZE(4))
	ACCESS	read-only
	STATUS	mandatory
	DESCRIPTION
		"This reports the physical location of this node on the ring.  
		Section 3.3.2.13 of IEEE 802.5 specification."
	::=  { s3TrNodeEntry 19 }

s3TrNodeEntFuncAddr OBJECT-TYPE
	SYNTAX	OCTET STRING (SIZE(6))
	ACCESS	read-only
	STATUS	mandatory
	DESCRIPTION
		"Specifies the functional addresses used by this station.  
		Section 3.3.2.8 of IEEE 802.5 specification."
	::=  { s3TrNodeEntry 20 }

s3TrNodeEntAuthFuncClass OBJECT-TYPE
	SYNTAX	OCTET STRING (SIZE(2))
	ACCESS	read-only
	STATUS	mandatory
	DESCRIPTION
		"This specifies the functional classes that are allowed to be 
		active in the station.  Section 3.3.2.3 of IEEE 802.5 
		specification."
	::=  { s3TrNodeEntry 21 }

s3TrNodeEntAuthAccPriority OBJECT-TYPE
	SYNTAX	OCTET STRING (SIZE(2))
	ACCESS	read-only
	STATUS	mandatory
	DESCRIPTION
		"The maximum priority this station is allowed to use.  Section 
		3.3.2.2 of IEEE 802.5 specification."
	::=  { s3TrNodeEntry 22 }

s3TrNodeEntGrpAddr OBJECT-TYPE
	SYNTAX	OCTET STRING (SIZE(6))
	ACCESS	read-only
	STATUS	mandatory
	DESCRIPTION
		"This contains the group address of this station.  Section 
		3.3.2.9 of IEEE 802.5 specification."
	::=  { s3TrNodeEntry 23 }

s3TrNodeEntStationId OBJECT-TYPE
	SYNTAX	OCTET STRING (SIZE(6))
	ACCESS	read-only
	STATUS	mandatory
	DESCRIPTION
		"This string is used to uniquely identify the station.  It may 
		be equal to the station's MAC address.  Section 3.3.2.21 of 
		IEEE 802.5 specification."
	::=  { s3TrNodeEntry 24 }

s3TrNodeEntBeaconType OBJECT-TYPE
	SYNTAX	INTEGER {
		reconfiguration(1),
		signal-loss(2),
		bit-streaming(3),
		contention-streaming(4)
	}
	ACCESS	read-only
	STATUS	mandatory
	DESCRIPTION
		"This specifies the type of beacon frame seen.  Section 
		3.3.2.4 of IEEE 802.5 specification." 
	::=  { s3TrNodeEntry 25 }

s3TrNodeBeaconCnt OBJECT-TYPE
	SYNTAX	Counter
	ACCESS	read-only
	STATUS	mandatory
	DESCRIPTION
		"Number of beacon frames that have been sent by this station."
	::=  { s3TrNodeEntry 26 }

s3TrNodeLastBeaconTime OBJECT-TYPE
	SYNTAX	TimeTicks
	ACCESS	read-only
	STATUS	mandatory
	DESCRIPTION
		"The time of the last beacon frame sent by this station."
	::=  { s3TrNodeEntry 27 }

s3TrNodeLastInsertTime OBJECT-TYPE
	SYNTAX	TimeTicks
	ACCESS	read-only
	STATUS	mandatory
	DESCRIPTION
		"The time of the last ring insertion by this station.  Time is 
		relative from the system uptime."
	::=  { s3TrNodeEntry 28 }

s3TrNodeFirstInsertTime OBJECT-TYPE
	SYNTAX	TimeTicks
	ACCESS	read-only
	STATUS	mandatory
	DESCRIPTION
		"The time of the first ring insertion by this station.  Time 
		is relative from the system uptime."
	::=  { s3TrNodeEntry 29 }

s3TrNodeLastDeinsertTime OBJECT-TYPE
	SYNTAX	TimeTicks
	ACCESS	read-only
	STATUS	mandatory
	DESCRIPTION
		"The time of the last ring deinsertion by this station.  Time 
		is relative from the system uptime."
	::=  { s3TrNodeEntry 30 }

s3TrNodeRemoveStation OBJECT-TYPE
	SYNTAX	INTEGER {
		other(1),	-- do nothing
		remove(2)	-- remove the MAC address 
	}
	ACCESS	read-write
	STATUS	mandatory
	DESCRIPTION
		"Removes the MAC address associated with this entry from the 
		ring by sending a REMOVE MAC frame if this object is written 
		to with remove(2)."
	::=  { s3TrNodeEntry 31 }



-- SECTION 6: Token Ring "RING" Group


s3TrRingStatus OBJECT-TYPE
	SYNTAX	INTEGER {
		beaconing(1),
		notbeaconing(2)
	}
	ACCESS	read-only
	STATUS	mandatory
	DESCRIPTION
		"The status of the ring."
	::=  { s3TrRingStats 1 }

s3TrRingFrmsRxOk OBJECT-TYPE
	SYNTAX	Counter
	ACCESS	read-only
	STATUS	mandatory
	DESCRIPTION
		"Number of frames received successfully by the NMM."
	::=  { s3TrRingStats 2 }

s3TrRingOctetsRxOk OBJECT-TYPE
	SYNTAX	Counter
	ACCESS	read-only
	STATUS	mandatory
	DESCRIPTION
		"Number of octets received successfully by the NMM."
	::=  { s3TrRingStats 3 }

s3TrRingBcastFrmsRxOk OBJECT-TYPE
	SYNTAX	Counter
	ACCESS	read-only
	STATUS	mandatory
	DESCRIPTION
		"Number of broadcast frames received successfully by the NMM."
	::=  { s3TrRingStats 4 }

s3TrRingLineErrs OBJECT-TYPE
	SYNTAX	Counter
	ACCESS	read-only
	STATUS	mandatory
	DESCRIPTION
		"Number of line errors.  Section 3.8.1 of IEEE 802.5 
		specification."
	::=  { s3TrRingStats 5 }

s3TrRingBurstErrs OBJECT-TYPE
	SYNTAX	Counter
	ACCESS	read-only
	STATUS	mandatory
	DESCRIPTION
		"Number of burst errors.  Section 3.8.3 of IEEE 802.5 specification."
	::=  { s3TrRingStats 6 }

s3TrRingAriFciErrs OBJECT-TYPE
	SYNTAX	Counter
	ACCESS	read-only
	STATUS	mandatory
	DESCRIPTION
		"Number of ARI FCI errors.  See AC errors, Section 3.8.4 of 
		IEEE 802.5 specification."
	::=  { s3TrRingStats 7 }

s3TrRingLostFrames OBJECT-TYPE
	SYNTAX	Counter
	ACCESS	read-only
	STATUS	mandatory
	DESCRIPTION
		"Number of frames lost.  Section 3.8.6 of IEEE 802.5 
		specification."
	::=  { s3TrRingStats 8 }

s3TrRingRcvCongestErrs OBJECT-TYPE
	SYNTAX	Counter
	ACCESS	read-only
	STATUS	mandatory
	DESCRIPTION
		"Number of receive congestion errors.  Section 3.8.7 of IEEE 
		802.5 specification."
	::=  { s3TrRingStats 9 }

s3TrRingFrmCopyErrs OBJECT-TYPE
	SYNTAX	Counter
	ACCESS	read-only
	STATUS	mandatory
	DESCRIPTION
		"Number of frame copy errors.  Section 3.8.8 of IEEE 802.5 
		specification."
	::=  { s3TrRingStats 10 }

s3TrRingTokenErrs OBJECT-TYPE
	SYNTAX	Counter
	ACCESS	read-only
	STATUS	mandatory
	DESCRIPTION
		"Number of token errors.  Section 3.8.10 of IEEE 802.5 
		specification."
	::=  { s3TrRingStats 11 }

s3TrRingInternalErrs OBJECT-TYPE
	SYNTAX	Counter
	ACCESS	read-only
	STATUS	mandatory
	DESCRIPTION
		"Number of internal errors.  Section 3.8.2 of IEEE 802.5 
		specification."
	::=  { s3TrRingStats 12 }

s3TrRingAbortTransErrs OBJECT-TYPE
	SYNTAX	Counter
	ACCESS	read-only
	STATUS	mandatory
	DESCRIPTION
		"Number of abort delimiter transmitted errors.  Section 3.8.5 
		of IEEE 802.5 specification."
	::=  { s3TrRingStats 13 }

s3TrRingFrequencyErrs OBJECT-TYPE
	SYNTAX	Counter
	ACCESS	read-only
	STATUS	mandatory
	DESCRIPTION
		"Number of frequency errors.  Section 3.8.9 of IEEE 802.5 
		specification."
	::=  { s3TrRingStats 14 }

s3TrRingBeaconCnt OBJECT-TYPE
	SYNTAX	Counter
	ACCESS	read-only
	STATUS	mandatory
	DESCRIPTION
		"Number of beacon frames that have been seen."
	::=  { s3TrRingStats 15 }

s3TrRingBeaconType OBJECT-TYPE
	SYNTAX	INTEGER {
		reconfiguration(1),
		signal-loss(2),
		bit-streaming(3),
		contention-streaming(4)
	}
	ACCESS	read-only
	STATUS	mandatory
	DESCRIPTION
		"This specifies the type of beacon frame seen.  Section 
		3.3.2.4 of IEEE 802.5 Specification."
	::=  { s3TrRingStats 16 }

s3TrRingLastBeaconTime OBJECT-TYPE
	SYNTAX	TimeTicks
	ACCESS	read-only
	STATUS	mandatory
	DESCRIPTION
		"The time of the last beacon frame sent on the ring.  Time is 
		relative from the system uptime."
	::=  { s3TrRingStats 17 }

s3TrRingBeaconStation OBJECT-TYPE
	SYNTAX	OCTET STRING (SIZE(6))
	ACCESS	read-only
	STATUS	mandatory
	DESCRIPTION
		"The MAC address of station last beaconing."
	::=  { s3TrRingStats 18 }


END
