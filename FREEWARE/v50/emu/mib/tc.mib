-- MIB created 1/17/96 13:42:06, by
--   SMIC (the next generation) version 1.6.29, November 22, 1994.

CISCO-TC DEFINITIONS ::= BEGIN

-- From file: "CISCO-TC.my"

IMPORTS
    ciscoModules, ciscoProducts
            FROM CISCO-SMI;

ciscoTextualConventions OBJECT IDENTIFIER ::= { ciscoModules 1 }
-- MODULE-IDENTITY
--  LastUpdated
--    9506070000Z
--  OrgName
--    Cisco Systems, Inc.
--  ContactInfo
--           Cisco Systems
--     Customer Service
--    
--    Postal: 170 W Tasman Drive
--     San Jose, CA  95134
--     USA
--    
--       Tel: +1 800 553-NETS
--    
--    E-mail: cs-snmp@cisco.com
--  Descr
--    This module defines textual conventions used throughout
--    cisco enterprise mibs.
--  RevDate
--    9506070000Z
--  RevDescr
--    Miscellaneous updates/corrections, including making
--    CiscoNetworkProtocol enumerations contiguous.

CiscoNetworkProtocol ::= INTEGER {
        ip(1),
        decnet(2),
        pup(3),
        chaos(4),
        xns(5),
        x121(6),
        appletalk(7),
        clns(8),
        lat(9),
        vines(10),
        cons(11),
        apollo(12),
        stun(13),
        novell(14),
        qllc(15),
        snapshot(16),
        bstun(17),
        x25pvc(18)
        }
-- TEXTUAL-CONVENTION
--  Status
--    mandatory
--  Descr
--    Represents the different types of network layer protocols.

CiscoNetworkAddress ::= OCTET STRING
-- TEXTUAL-CONVENTION
--  DspHint
--    1x:
--  Status
--    mandatory
--  Descr
--    Represents a network layer address.  The length and format of
--    the address is protocol dependent as follows:
--    ip  4 octets
--    decnet  2 octets
--    pup  obsolete
--    chaos  2 octets
--    xns  10 octets
--      first 4 octets are the net number
--      last 6 octets are the host number
--    x121 
--    appletalk 3 octets
--      first 2 octets are the net number
--      last octet is the host number
--    clns
--    lat
--    vines  6 octets
--      first 4 octets are the net number
--      last 2 octets are the host number
--    cons
--    apollo  10 octets
--      first 4 octets are the net number
--      last 6 octets are the host number
--    stun   8 octets
--    novell  10 octets
--      first 4 octets are the net number
--      last 6 octets are the host number
--    qllc  6 octets
--    bstun  1 octet - bi-sync serial tunnel 
--    snapshot 1 octet
--    x25 pvc  2 octets (12 bits)


END
