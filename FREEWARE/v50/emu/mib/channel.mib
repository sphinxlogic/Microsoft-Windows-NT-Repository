-- MIB created 1/17/96 13:42:01, by
--   SMIC (the next generation) version 1.6.29, November 22, 1994.

CISCO-CHANNEL-MIB DEFINITIONS ::= BEGIN

-- From file: "CISCO-CHANNEL-MIB.my"

IMPORTS
    Counter32, Integer32, IpAddress
            FROM SNMPv2-SMI-v1
    OBJECT-TYPE
            FROM RFC-1212
    TRAP-TYPE
            FROM RFC-1215
    DisplayString, TruthValue, TimeStamp
            FROM SNMPv2-TC-v1
    ciscoMgmt
            FROM CISCO-SMI;

channel OBJECT IDENTIFIER ::= { ciscoMgmt 20 }
-- MODULE-IDENTITY
--  LastUpdated
--    9508150000Z
--  OrgName
--    cisco IBM engineering Working Group
--  ContactInfo
--     
--     Mauro Zallocco (editor)
--     cisco Systems, Inc.
--                          1525 O'Brien Dr.
--                          Menlo Park, CA 94025
--                          mzallocc@cisco.com
--  Descr
--    This is the MIB module for objects used to manage
--                   the cisco channel interface processor (CIP) card.
--  RevDate
--    9508150000Z
--  RevDescr
--    Specify a correct (non-negative) range for several
--    index objects.
--  RevDate
--    9411170000Z
--  RevDescr
--    Changed from CHANNEL-MIB to CISCO-CHANNEL-MIB.

cipCard         OBJECT IDENTIFIER ::= { channel 1 }
cipCardClaw     OBJECT IDENTIFIER ::= { cipCard 4 }
cipCardTraps    OBJECT IDENTIFIER ::= { cipCard 5 }

cipCardTable OBJECT-TYPE
    SYNTAX SEQUENCE OF CipCardEntry
    ACCESS not-accessible
    STATUS mandatory
    DESCRIPTION
        "This table contains a list of values for the
         CIP card which can be accessed to 
         determine the general state of the CIP.
         
         This table extends CardTable in the cisco.mib"
    ::= { cipCard 1 }

cipCardEntry OBJECT-TYPE
    SYNTAX CipCardEntry
    ACCESS not-accessible
    STATUS mandatory
    DESCRIPTION
        "A list of values for a CIP Card. 
        
         This extends cardTableEntry in the cisco.mib"
    INDEX { cipCardEntryIndex }
    ::= { cipCardTable 1 }

CipCardEntry ::= SEQUENCE {
    cipCardEntryIndex Integer32(0..2147483647),
    cipCardEntryName DisplayString,
    cipCardEntryTotalMemory Integer32,
    cipCardEntryFreeMemory Integer32,
    cipCardEntryCpuUtilization INTEGER,
    cipCardEntryTimeSinceLastReset Counter32
    }

cipCardEntryIndex OBJECT-TYPE
    SYNTAX Integer32(0..2147483647)
    ACCESS not-accessible
    STATUS mandatory
    DESCRIPTION
        "Index into cardTable (not physical chassis
        slot number, matches cisco chassis MIB cardindex)."
    ::= { cipCardEntry 1 }

cipCardEntryName OBJECT-TYPE
    SYNTAX DisplayString
--    Rsyntax OCTET STRING(SIZE(0..255))
    ACCESS read-write
    STATUS mandatory
    DESCRIPTION
        "The configured name for the CIP."
    ::= { cipCardEntry 2 }

cipCardEntryTotalMemory OBJECT-TYPE
    SYNTAX Integer32
--  Units
--    kilo bytes
    ACCESS read-only
    STATUS mandatory
    DESCRIPTION
        "Total memory on the card."
    ::= { cipCardEntry 3 }

cipCardEntryFreeMemory OBJECT-TYPE
    SYNTAX Integer32
--  Units
--    kilo bytes
    ACCESS read-only
    STATUS mandatory
    DESCRIPTION
        "Total free memory on the card, that is the
         amount of memory not in use."
    ::= { cipCardEntry 4 }

cipCardEntryCpuUtilization OBJECT-TYPE
    SYNTAX INTEGER(0..100)
    ACCESS read-only
    STATUS mandatory
    DESCRIPTION
        "The average, over the last minute, of the
         percentage of time that this processor was not
         idle."
    ::= { cipCardEntry 5 }

cipCardEntryTimeSinceLastReset OBJECT-TYPE
    SYNTAX Counter32
--  Units
--    seconds
    ACCESS read-only
    STATUS mandatory
    DESCRIPTION
        "The amount of time the CIP has been running."
    ::= { cipCardEntry 6 }

cipCardDaughterBoardTable OBJECT-TYPE
    SYNTAX SEQUENCE OF CipCardDaughterBoardEntry
    ACCESS not-accessible
    STATUS mandatory
    DESCRIPTION
        "This table contains a list of objects pertaining to
         the daughter board on the CIP card."
    ::= { cipCard 2 }

cipCardDaughterBoardEntry OBJECT-TYPE
    SYNTAX CipCardDaughterBoardEntry
    ACCESS not-accessible
    STATUS mandatory
    DESCRIPTION
        "A list of daughter board values."
    INDEX { cipCardEntryIndex, cipCardDtrBrdIndex }
    ::= { cipCardDaughterBoardTable 1 }

CipCardDaughterBoardEntry ::= SEQUENCE {
    cipCardDtrBrdIndex Integer32(0..2147483647),
    cipCardDtrBrdType INTEGER,
    cipCardDtrBrdStatus TruthValue,
    cipCardDtrBrdSignal TruthValue,
    cipCardDtrBrdOnline TruthValue,
    implicitIncidents Counter32,
    codeViolationErrors Counter32,
    linkFailureSignalOrSyncLoss Counter32,
    linkFailureNOSs Counter32,
    linkFailureSequenceTimeouts Counter32,
    linkFailureInvalidSequences Counter32,
    linkIncidentTrapCause INTEGER
    }

cipCardDtrBrdIndex OBJECT-TYPE
    SYNTAX Integer32(0..2147483647)
    ACCESS not-accessible
    STATUS mandatory
    DESCRIPTION
        "This indicates which daughter board is
         is being referenced for a particular CIP card."
    ::= { cipCardDaughterBoardEntry 1 }

cipCardDtrBrdType OBJECT-TYPE
    SYNTAX INTEGER {
        escon(1),
        busAndTag(2)
        }
    ACCESS read-only
    STATUS mandatory
    DESCRIPTION
        "This indicates the channel path interface type."
    ::= { cipCardDaughterBoardEntry 2 }

cipCardDtrBrdStatus OBJECT-TYPE
    SYNTAX TruthValue
--    Rsyntax INTEGER {
--        true(1),
--        false(2)
--        }
    ACCESS read-only
    STATUS mandatory
    DESCRIPTION
        "cipCardDtrBrdStatus is true when the
         microcode for the daughter board has been
         successfully loaded and is executing, false
         otherwise."
    ::= { cipCardDaughterBoardEntry 3 }

cipCardDtrBrdSignal OBJECT-TYPE
    SYNTAX TruthValue
--    Rsyntax INTEGER {
--        true(1),
--        false(2)
--        }
    ACCESS read-only
    STATUS mandatory
    DESCRIPTION
        "For ESCON, cipCardDtrBrdSignal is true when 
         light has been seen on the fiber and synchronization 
         has been established, false otherwise.
         
         For the Parallel Channel Adapter (PCA) which provides
         the Bus and Tag connection, cipCardDtrBrdSignal is 
         true when Operational out has been sensed, false 
         otherwise."
    ::= { cipCardDaughterBoardEntry 4 }

cipCardDtrBrdOnline OBJECT-TYPE
    SYNTAX TruthValue
--    Rsyntax INTEGER {
--        true(1),
--        false(2)
--        }
    ACCESS read-only
    STATUS mandatory
    DESCRIPTION
        "For ESCON, cipCardDtrBrdOnline is true when a path 
         has been established with at least one channel,
         false otherwise.
         
         For PCA, cipCardDtrBrdOnline is true when the PCA
         is online to the channel. It will respond to at
         least one device address"
    ::= { cipCardDaughterBoardEntry 5 }

implicitIncidents OBJECT-TYPE
    SYNTAX Counter32
    ACCESS read-only
    STATUS mandatory
    DESCRIPTION
        "This counts the number of times the ESCON Processor
         recovers from an internal error."
    ::= { cipCardDaughterBoardEntry 6 }

codeViolationErrors OBJECT-TYPE
    SYNTAX Counter32
    ACCESS read-only
    STATUS mandatory
    DESCRIPTION
        "The number of recognized code-violation errors.
         A trap is issued when this number exceeds the bit
         error rate threshold for ESCON. The bit 
         error rate threshold is set at 15 error burst 
         within a 5 minute period. An error burst is the
         time period of 1.5 seconds plus or minus 0.05 
         seconds during which one or more code violations
         errors occur."
    ::= { cipCardDaughterBoardEntry 7 }

linkFailureSignalOrSyncLoss OBJECT-TYPE
    SYNTAX Counter32
    ACCESS read-only
    STATUS mandatory
    DESCRIPTION
        "The number of link failures recognized as a
         result of a loss of signal or loss of 
         synchronization that persisted longer than the
         link interval duration, the link interval 
         duration is one second with a tolerance of +1.5
         seconds and -0 seconds."
    ::= { cipCardDaughterBoardEntry 8 }

linkFailureNOSs OBJECT-TYPE
    SYNTAX Counter32
    ACCESS read-only
    STATUS mandatory
    DESCRIPTION
        "The number of link failures recognized as a result of
         the not-operational sequence (NOS)."
    ::= { cipCardDaughterBoardEntry 9 }

linkFailureSequenceTimeouts OBJECT-TYPE
    SYNTAX Counter32
    ACCESS read-only
    STATUS mandatory
    DESCRIPTION
        "The number of link failures recognized as a result of
         a connection recovery timeout or response timeout 
         occurring while in transmit OLS state."
    ::= { cipCardDaughterBoardEntry 10 }

linkFailureInvalidSequences OBJECT-TYPE
    SYNTAX Counter32
    ACCESS read-only
    STATUS mandatory
    DESCRIPTION
        "The number of link failures recognized as a result of
         an invalid sequence for Link-Level-Facility State.
         Either a UD or UDR sequence was recognized while in
         wait-for-offline-sequence state."
    ::= { cipCardDaughterBoardEntry 11 }

linkIncidentTrapCause OBJECT-TYPE
    SYNTAX INTEGER {
        liOther(1),
        liStatus(2),
        liImplicitIncidents(3),
        liBERthreshold(4),
        liSignalOrSyncLoss(5),
        liNotOperationalSequence(6),
        liSequenceTimeouts(7),
        liInvalidSequences(8)
        }
    ACCESS read-only
    STATUS mandatory
    DESCRIPTION
        "This indicates the reason for the last link
         failure.
         
         liStatus indicates that the daughter board status
         has changed.
         
         liImplicitIncident indicates that a condition which
         may cause the recognition of a link incident in the
         attached node has been recognized.
         
         liBERthreshold indicates that the code violation
         error rate exceeded the threshold. 
         
         liSignalOrSyncLoss indicates a loss of signal or 
         loss of synchronization that persisted longer 
         than the link interval duration.
         
         liNotOperationalSequence indicates the recognition
         of not-operational sequence, usually due to the
         operator taking the channel offline.
         
         liSequenceTimeout indicates a connection recovery
         timeout or response timeout occurring while in
         transmit OLS state.
         
         linvalidSequence indicates a UD or UDR sequence was
         recognized while in wait-for-offline-sequence state.
         "
    ::= { cipCardDaughterBoardEntry 12 }

cipCardSubChannelTable OBJECT-TYPE
    SYNTAX SEQUENCE OF CipCardSubChannelEntry
    ACCESS not-accessible
    STATUS mandatory
    DESCRIPTION
        "This table contains a list of objects pertaining to
         each host connection."
    ::= { cipCard 3 }

cipCardSubChannelEntry OBJECT-TYPE
    SYNTAX CipCardSubChannelEntry
    ACCESS not-accessible
    STATUS mandatory
    DESCRIPTION
        "A list of host connection statistics."
    INDEX { cipCardEntryIndex, cipCardDtrBrdIndex, cipCardSubChannelIndex }
    ::= { cipCardSubChannelTable 1 }

CipCardSubChannelEntry ::= SEQUENCE {
    cipCardSubChannelIndex Integer32(0..2147483647),
    cipCardSubChannelConnections Counter32,
    cipCardSubChannelCancels Counter32,
    cipCardSubChannelSelectiveResets Counter32,
    cipCardSubChannelSystemResets Counter32,
    cipCardSubChannelDeviceErrors Counter32,
    cipCardSubChannelWriteBlocksDropped Counter32,
    cipCardSubChannelLastSenseData OCTET STRING(SIZE(2)),
    cipCardSubChannelLastSenseDataTime TimeStamp,
    cipCardSubChannelCuBusies Counter32
    }

cipCardSubChannelIndex OBJECT-TYPE
    SYNTAX Integer32(0..2147483647)
    ACCESS read-only
    STATUS mandatory
    DESCRIPTION
        "This indicates which subchannel is being referenced
         for a particular daughter board on a CIP card ."
    ::= { cipCardSubChannelEntry 1 }

cipCardSubChannelConnections OBJECT-TYPE
    SYNTAX Counter32
    ACCESS read-only
    STATUS mandatory
    DESCRIPTION
        "Number of times a device was connected to the
         subchannel. For some devices, this correlates with
         the number of start subchannels."
    ::= { cipCardSubChannelEntry 2 }

cipCardSubChannelCancels OBJECT-TYPE
    SYNTAX Counter32
    ACCESS read-only
    STATUS mandatory
    DESCRIPTION
        "Number of halt subchannels."
    ::= { cipCardSubChannelEntry 3 }

cipCardSubChannelSelectiveResets OBJECT-TYPE
    SYNTAX Counter32
    ACCESS read-only
    STATUS mandatory
    DESCRIPTION
        "Number of selective resets."
    ::= { cipCardSubChannelEntry 4 }

cipCardSubChannelSystemResets OBJECT-TYPE
    SYNTAX Counter32
    ACCESS read-only
    STATUS mandatory
    DESCRIPTION
        "Number of system resets."
    ::= { cipCardSubChannelEntry 5 }

cipCardSubChannelDeviceErrors OBJECT-TYPE
    SYNTAX Counter32
    ACCESS read-only
    STATUS mandatory
    DESCRIPTION
        "Number of device level errors."
    ::= { cipCardSubChannelEntry 6 }

cipCardSubChannelWriteBlocksDropped OBJECT-TYPE
    SYNTAX Counter32
    ACCESS read-only
    STATUS mandatory
    DESCRIPTION
        "Number of times a block was received by the channel
         and a router buffer was not available so the block 
         was discarded."
    ::= { cipCardSubChannelEntry 7 }

cipCardSubChannelLastSenseData OBJECT-TYPE
    SYNTAX OCTET STRING(SIZE(2))
    ACCESS read-only
    STATUS mandatory
    DESCRIPTION
        "This is the last sense data sent to the channel 
         by this device."
    ::= { cipCardSubChannelEntry 8 }

cipCardSubChannelLastSenseDataTime OBJECT-TYPE
    SYNTAX TimeStamp
--    Rsyntax TimeTicks
    ACCESS read-only
    STATUS mandatory
    DESCRIPTION
        "This indicates the time when the last sense data
         was sent to the channel by this device."
    ::= { cipCardSubChannelEntry 9 }

cipCardSubChannelCuBusies OBJECT-TYPE
    SYNTAX Counter32
    ACCESS read-only
    STATUS mandatory
    DESCRIPTION
        "This is the number of control unit busies sent to the
         channel when this device was requested."
    ::= { cipCardSubChannelEntry 10 }

cipCardClawTable OBJECT-TYPE
    SYNTAX SEQUENCE OF CipCardClawEntry
    ACCESS not-accessible
    STATUS mandatory
    DESCRIPTION
        "This table contains status and other information 
         not covered in the following tables for the Common 
         Link Access to Workstation (CLAW) protocol."
    ::= { cipCardClaw 1 }

cipCardClawEntry OBJECT-TYPE
    SYNTAX CipCardClawEntry
    ACCESS not-accessible
    STATUS mandatory
    DESCRIPTION
        "A list of CLAW values."
    INDEX { cipCardEntryIndex, cipCardDtrBrdIndex, cipCardSubChannelIndex, cipCardClawIndex }
    ::= { cipCardClawTable 1 }

CipCardClawEntry ::= SEQUENCE {
    cipCardClawIndex Integer32(0..2147483647),
    cipCardClawConnected TruthValue
    }

cipCardClawIndex OBJECT-TYPE
    SYNTAX Integer32(0..2147483647)
    ACCESS read-only
    STATUS mandatory
    DESCRIPTION
        "This indicates which CLAW link is being referenced
         for a particular subchannel on a daughter board on a
         CIP card."
    ::= { cipCardClawEntry 1 }

cipCardClawConnected OBJECT-TYPE
    SYNTAX TruthValue
--    Rsyntax INTEGER {
--        true(1),
--        false(2)
--        }
    ACCESS read-only
    STATUS mandatory
    DESCRIPTION
        "Indicates CLAW connection status."
    ::= { cipCardClawEntry 2 }

cipCardClawConfigTable OBJECT-TYPE
    SYNTAX SEQUENCE OF CipCardClawConfigEntry
    ACCESS not-accessible
    STATUS mandatory
    DESCRIPTION
        "This table contains configuration information for
         the Common Link Access to Workstation (CLAW)
         protocol."
    ::= { cipCardClaw 2 }

cipCardClawConfigEntry OBJECT-TYPE
    SYNTAX CipCardClawConfigEntry
    ACCESS not-accessible
    STATUS mandatory
    DESCRIPTION
        "A list of CLAW configuration values."
    INDEX { cipCardEntryIndex, cipCardDtrBrdIndex, cipCardSubChannelIndex, cipCardClawIndex }
    ::= { cipCardClawConfigTable 1 }

CipCardClawConfigEntry ::= SEQUENCE {
    cipCardClawConfigPath OCTET STRING(SIZE(2)),
    cipCardClawConfigDevice OCTET STRING(SIZE(2)),
    cipCardClawConfigIpAddr IpAddress,
    cipCardClawConfigHostName DisplayString(SIZE(1..10)),
    cipCardClawConfigRouterName DisplayString(SIZE(1..10)),
    cipCardClawConfigHostAppl DisplayString(SIZE(1..10)),
    cipCardClawConfigRouterAppl DisplayString(SIZE(1..10))
    }

cipCardClawConfigPath OBJECT-TYPE
    SYNTAX OCTET STRING(SIZE(2))
    ACCESS read-write
    STATUS mandatory
    DESCRIPTION
        "Hex path identifier for the switch port containing 
         the fiber from the  channel on the host to which 
         this task connects. This is a concatenation of the 
         switch port number, the channel logical address, and
         the control unit logical address. For a directly 
         connected channel, the switch port number is usually
         01."
    ::= { cipCardClawConfigEntry 1 }

cipCardClawConfigDevice OBJECT-TYPE
    SYNTAX OCTET STRING(SIZE(2))
    ACCESS read-write
    STATUS mandatory
    DESCRIPTION
        "Device address for the device the host will use to
         communicate with this task."
    ::= { cipCardClawConfigEntry 2 }

cipCardClawConfigIpAddr OBJECT-TYPE
    SYNTAX IpAddress
    ACCESS read-write
    STATUS mandatory
    DESCRIPTION
        "IP address of the host application for this task."
    ::= { cipCardClawConfigEntry 3 }

cipCardClawConfigHostName OBJECT-TYPE
    SYNTAX DisplayString
--    Rsyntax OCTET STRING(SIZE(0..255))
    ACCESS read-write
    STATUS mandatory
    DESCRIPTION
        "CLAW host name for this CLAW device."
    ::= { cipCardClawConfigEntry 4 }

cipCardClawConfigRouterName OBJECT-TYPE
    SYNTAX DisplayString
--    Rsyntax OCTET STRING(SIZE(0..255))
    ACCESS read-write
    STATUS mandatory
    DESCRIPTION
        "CLAW router name for this CLAW device."
    ::= { cipCardClawConfigEntry 5 }

cipCardClawConfigHostAppl OBJECT-TYPE
    SYNTAX DisplayString
--    Rsyntax OCTET STRING(SIZE(0..255))
    ACCESS read-write
    STATUS mandatory
    DESCRIPTION
        "CLAW host application name for this CLAW connection."
    ::= { cipCardClawConfigEntry 6 }

cipCardClawConfigRouterAppl OBJECT-TYPE
    SYNTAX DisplayString
--    Rsyntax OCTET STRING(SIZE(0..255))
    ACCESS read-write
    STATUS mandatory
    DESCRIPTION
        "CLAW router application name for this CLAW
         connection."
    ::= { cipCardClawConfigEntry 7 }

cipCardClawDataXferStatsTable OBJECT-TYPE
    SYNTAX SEQUENCE OF CipCardClawDataXferStatsEntry
    ACCESS not-accessible
    STATUS mandatory
    DESCRIPTION
        "This table contains a list of objects pertaining to
         data transfer statistics per CLAW Logical Link."
    ::= { cipCardClaw 3 }

cipCardClawDataXferStatsEntry OBJECT-TYPE
    SYNTAX CipCardClawDataXferStatsEntry
    ACCESS not-accessible
    STATUS mandatory
    DESCRIPTION
        "A list of daughter board statistics."
    INDEX { cipCardEntryIndex, cipCardDtrBrdIndex, cipCardSubChannelIndex, cipCardClawIndex }
    ::= { cipCardClawDataXferStatsTable 1 }

CipCardClawDataXferStatsEntry ::= SEQUENCE {
    cipCardClawDataXferStatsBlocksRead Counter32,
    cipCardClawDataXferStatsBlocksWritten Counter32,
    cipCardClawDataXferStatsBytesRead Counter32,
    cipCardClawDataXferStatsBytesWritten Counter32,
    cipCardClawDataXferStatsReadBlocksDropped Counter32,
    cipCardClawDataXferStatsWriteBlocksDropped Counter32,
    cipCardClawDataXferStatsBufferGetRetryCount Counter32
    }

cipCardClawDataXferStatsBlocksRead OBJECT-TYPE
    SYNTAX Counter32
    ACCESS read-only
    STATUS mandatory
    DESCRIPTION
        "Number of successful read data transfer channel
         command words (CCWs) from the channel perspective."
    ::= { cipCardClawDataXferStatsEntry 1 }

cipCardClawDataXferStatsBlocksWritten OBJECT-TYPE
    SYNTAX Counter32
    ACCESS read-only
    STATUS mandatory
    DESCRIPTION
        "Number of successful write data transfer CCWs
         from the channel perspective."
    ::= { cipCardClawDataXferStatsEntry 2 }

cipCardClawDataXferStatsBytesRead OBJECT-TYPE
    SYNTAX Counter32
    ACCESS read-only
    STATUS mandatory
    DESCRIPTION
        "Number of bytes successfully read from the 
         channel perspective."
    ::= { cipCardClawDataXferStatsEntry 3 }

cipCardClawDataXferStatsBytesWritten OBJECT-TYPE
    SYNTAX Counter32
    ACCESS read-only
    STATUS mandatory
    DESCRIPTION
        "Number of bytes successfully written from the 
         channel perspective."
    ::= { cipCardClawDataXferStatsEntry 5 }

cipCardClawDataXferStatsReadBlocksDropped OBJECT-TYPE
    SYNTAX Counter32
    ACCESS read-only
    STATUS mandatory
    DESCRIPTION
        "Number of read blocks dropped."
    ::= { cipCardClawDataXferStatsEntry 7 }

cipCardClawDataXferStatsWriteBlocksDropped OBJECT-TYPE
    SYNTAX Counter32
    ACCESS read-only
    STATUS mandatory
    DESCRIPTION
        "Number of write blocks dropped."
    ::= { cipCardClawDataXferStatsEntry 8 }

cipCardClawDataXferStatsBufferGetRetryCount OBJECT-TYPE
    SYNTAX Counter32
    ACCESS read-only
    STATUS mandatory
    DESCRIPTION
        "Number of times a buffer was requested and none were
         available."
    ::= { cipCardClawDataXferStatsEntry 9 }

cipCardLinkFailure TRAP-TYPE
--?? Non-reverse mappable trap
    ENTERPRISE cipCardTraps
    VARIABLES {
        cipCardDtrBrdIndex, cipCardDtrBrdStatus, 
        cipCardDtrBrdSignal, linkIncidentTrapCause, 
        implicitIncidents, codeViolationErrors, 
        linkFailureSignalOrSyncLoss, linkFailureNOSs, 
        linkFailureSequenceTimeouts, linkFailureInvalidSequences }
--  Status
--    mandatory
    DESCRIPTION
        "This trap indicates that a significant link event has been recognized
         resulting in the degradation of the interface line quality."
    ::= 1


END
