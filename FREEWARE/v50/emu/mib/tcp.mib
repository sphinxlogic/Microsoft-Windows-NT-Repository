-- MIB created 1/17/96 13:42:09, by
--   SMIC (the next generation) version 1.6.29, November 22, 1994.

CISCO-TCP-MIB DEFINITIONS ::= BEGIN

-- From file: "CISCO-TCP-MIB.my"

IMPORTS
    TimeTicks, Integer32, Counter32
            FROM SNMPv2-SMI-v1
    OBJECT-TYPE
            FROM RFC-1212
    tcpConnLocalAddress,
    tcpConnLocalPort,
    tcpConnRemAddress,
    tcpConnRemPort
            FROM RFC1213-MIB
    ciscoMgmt
            FROM CISCO-SMI;

ciscoTcpMIB OBJECT IDENTIFIER ::= { ciscoMgmt 6 }
-- MODULE-IDENTITY
--  LastUpdated
--    9407210000Z
--  OrgName
--    Cisco Systems, Inc.
--  ContactInfo
--     Cisco Systems
--     Customer Service
--    
--    Postal: 170 W. Tasman Drive
--     San Jose, CA  95134
--     USA
--    
--       Tel: +1 800 553-NETS
--    
--    E-mail: cs-snmp@cisco.com
--  RevDate
--    9407210000Z
--  RevDescr
--    Initial version of this MIB module.

ciscoTcpMIBObjects OBJECT IDENTIFIER ::= { ciscoTcpMIB 1 }
ciscoTcpMIBTraps OBJECT IDENTIFIER ::= { ciscoTcpMIB 2 }
ciscoTcpMIBConformance OBJECT IDENTIFIER ::= { ciscoTcpMIB 3 }
ciscoTcpMIBCompliances OBJECT IDENTIFIER ::= { ciscoTcpMIBConformance 1 }
ciscoTcpMIBGroups OBJECT IDENTIFIER ::= { ciscoTcpMIBConformance 2 }

ciscoTcpConnTable OBJECT-TYPE
    SYNTAX SEQUENCE OF CiscoTcpConnEntry
    ACCESS not-accessible
    STATUS mandatory
    DESCRIPTION
        "A table containing TCP connection-specific information."
    ::= { ciscoTcpMIBObjects 1 }

ciscoTcpConnEntry OBJECT-TYPE
    SYNTAX CiscoTcpConnEntry
    ACCESS not-accessible
    STATUS mandatory
    DESCRIPTION
        "Additional information about a particular current TCP
        connection beyond that provided by MIB-II's tcpConnEntry.
        An object of this type is transient, in that it ceases to
        exist when (or soon after) the connection makes the transition
        to the CLOSED state."
    INDEX { tcpConnLocalAddress, tcpConnLocalPort, tcpConnRemAddress, tcpConnRemPort }
-- Augments tcpConnEntry FROM RFC1213-MIB
    ::= { ciscoTcpConnTable 1 }

CiscoTcpConnEntry ::= SEQUENCE {
    ciscoTcpConnInBytes Counter32,
    ciscoTcpConnOutBytes Counter32,
    ciscoTcpConnInPkts Counter32,
    ciscoTcpConnOutPkts Counter32,
    ciscoTcpConnElapsed TimeTicks,
    ciscoTcpConnSRTT Integer32
    }

ciscoTcpConnInBytes OBJECT-TYPE
    SYNTAX Counter32
    ACCESS read-only
    STATUS mandatory
    DESCRIPTION
        "Number of bytes that have been input on this TCP
        connection."
    ::= { ciscoTcpConnEntry 1 }

ciscoTcpConnOutBytes OBJECT-TYPE
    SYNTAX Counter32
    ACCESS read-only
    STATUS mandatory
    DESCRIPTION
        "Number of bytes that have been output on this TCP
        connection."
    ::= { ciscoTcpConnEntry 2 }

ciscoTcpConnInPkts OBJECT-TYPE
    SYNTAX Counter32
    ACCESS read-only
    STATUS mandatory
    DESCRIPTION
        "Number of packets that have been input on this TCP
        connection."
    ::= { ciscoTcpConnEntry 3 }

ciscoTcpConnOutPkts OBJECT-TYPE
    SYNTAX Counter32
    ACCESS read-only
    STATUS mandatory
    DESCRIPTION
        "Number of packets that have been output on this TCP
        connection."
    ::= { ciscoTcpConnEntry 4 }

ciscoTcpConnElapsed OBJECT-TYPE
    SYNTAX TimeTicks
    ACCESS read-only
    STATUS mandatory
    DESCRIPTION
        "Amount of time this TCP connection has been established."
    ::= { ciscoTcpConnEntry 5 }

ciscoTcpConnSRTT OBJECT-TYPE
    SYNTAX Integer32
--  Units
--    milliseconds
    ACCESS read-only
    STATUS mandatory
    DESCRIPTION
        "`Smoothed' round-trip time for this TCP connection."
    ::= { ciscoTcpConnEntry 6 }

ciscoTcpMIBGroup OBJECT IDENTIFIER ::= { ciscoTcpMIBGroups 1 }
-- OBJECT-GROUP
--  Status
--    mandatory
--  Descr
--    A collection of objects providing TCP connection
--    monitoring.
--  objects
--    ciscoTcpConnInBytes, ciscoTcpConnOutBytes, ciscoTcpConnInPkts, 
--    ciscoTcpConnOutPkts, ciscoTcpConnElapsed, ciscoTcpConnSRTT

ciscoTcpMIBCompliance OBJECT IDENTIFIER ::= { ciscoTcpMIBCompliances 1 }
-- MODULE-COMPLIANCE
--  Status
--    mandatory
--  Descr
--    The compliance statement for entities which implement
--    the Cisco TCP MIB
--  Module
--    >>current<<
--   MandGroup
--    ciscoTcpMIBGroup


END
