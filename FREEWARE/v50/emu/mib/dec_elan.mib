DEC-ELAN-MIB DEFINITIONS ::= BEGIN 
 
    IMPORTS 
           Counter, enterprises, IpAddress 
                   FROM RFC1155-SMI 
           OBJECT-TYPE 
                   FROM RFC-1212 
           DisplayString 
                   FROM RFC1286-BRIDGE
                   FROM RFC1213-MIB; 
--  DEC-MIB { iso org(3) dod(6) internet(1) private (4) enterprises(1) 36 } 
 
    dec             OBJECT IDENTIFIER ::= { enterprises 36 } 
    ema             OBJECT IDENTIFIER ::= { dec 2 } 
    decMIBextension OBJECT IDENTIFIER ::= { ema 18 } 
    elanext         OBJECT IDENTIFIER ::= { decMIBextension 1 } 
    efddi           OBJECT IDENTIFIER ::= { elanext 1 } 
    esystem         OBJECT IDENTIFIER ::= { elanext 2 } 
    einterfaces     OBJECT IDENTIFIER ::= { elanext 3 } 
    ebridge         OBJECT IDENTIFIER ::= { elanext 4 } 
    eauth           OBJECT IDENTIFIER ::= { elanext 5 } 
 
 
    -- 
    -- efddi   - groups in the extended FDDI module 
    -- 
    -- objects in the Digital FDDI implementation over and above 
    -- those in the FDDI MIB. 
 
    efddiSMT          OBJECT IDENTIFIER ::= { efddi 1 } 
    efddiMAC          OBJECT IDENTIFIER ::= { efddi 2 } 
    efddiPORT         OBJECT IDENTIFIER ::= { efddi 3 } 
    efddiFDX          OBJECT IDENTIFIER ::= { efddi 4 } 
 
    -- efddiSMTTable  - the extended SMT table 
    -- these are objects implemented in Digital implementations over 
    -- and above the standard SMT group in the IETF FDDI MIB. 
 
    efddiSMTTable OBJECT-TYPE 
        SYNTAX  SEQUENCE OF EfddiSMTEntry 
        ACCESS  not-accessible 
        STATUS  mandatory 
        DESCRIPTION 
               "A list of SMT entries.  The number of entries is given 
               by smtNumber, defined in the FDDI MIB." 
    ::= { efddiSMT 1 } 
 
    efddiSMTEntry OBJECT-TYPE 
        SYNTAX  EfddiSMTEntry 
        ACCESS  not-accessible 
        STATUS  mandatory 
        DESCRIPTION 
               "A collection of objects containing information for a 
               given SMT link." 
        INDEX  { eSMTIndex } 
        ::= { efddiSMTTable 1 } 
 
    EfddiSMTEntry ::= 
        SEQUENCE { 
            eSMTIndex 
                INTEGER, 
            eSMTStationType 
                INTEGER, 
            eSMTTracesReceived 
                Counter 
                 } 
 
    eSMTIndex OBJECT-TYPE 
 
 
        SYNTAX  INTEGER 
        ACCESS  read-only 
        STATUS  mandatory 
        DESCRIPTION 
               "Identifies the SMT Index.  The value of this object is 
               the same as the snmpFddiSMTIndex, defined in the FDDI MIB, 
               for this smt entity." 
        ::= { efddiSMTEntry 1 } 
 
    eSMTStationType OBJECT-TYPE 
        SYNTAX  INTEGER { 
                           sas(1), 
                           dac(2), 
                           sac(3), 
                           nac(4), 
                           das(5) 
                        } 
        ACCESS  read-only 
        STATUS  mandatory 
        DESCRIPTION 
               "The Station Type Identification." 
        ::= { efddiSMTEntry 2 } 
 
    eSMTTracesReceived OBJECT-TYPE 
        SYNTAX  Counter 
        ACCESS  read-only 
        STATUS  mandatory 
        DESCRIPTION 
               "The number of PC Traces received by this station." 
        ::= { efddiSMTEntry 3 } 
 
    -- efddiMACTable  - the extended MAC table 
    -- these are objects implemented in Digital implementations over 
    -- and above the standard MAC group in the IETF FDDI MIB. 
 
    efddiMACTable OBJECT-TYPE 
        SYNTAX  SEQUENCE OF EfddiMACEntry 
        ACCESS  not-accessible 
        STATUS  mandatory 
        DESCRIPTION 
               "A list of MAC entries.  The number of entries is given 
               by macNumber, defined in the FDDI MIB." 
        ::= { efddiMAC 1 } 
 
 
    efddiMACEntry OBJECT-TYPE 
        SYNTAX  EfddiMACEntry 
        ACCESS  not-accessible 
        STATUS  mandatory 
        DESCRIPTION 
               "A collection of objects containing information for a 
               given MAC entity." 
        INDEX  { eMACSMTIndex, eMACIndex } 
        ::= { efddiMACTable 1 } 
 
    EfddiMACEntry ::= 
        SEQUENCE { 
            eMACSMTIndex 
                INTEGER, 
            eMACIndex 
                INTEGER, 
            eMACLinkIndex 
                INTEGER, 
            eMACLinkState 
                INTEGER, 
            eMACRingPurgerState 
                INTEGER, 
            eMACRingPurgerEnable 
                INTEGER, 
            eMACRingPurgeErrors 
                Counter, 
            eMACFrameStripMode 
                INTEGER, 
            eMACFCIStripErrors 
                Counter, 
            eMACRingErrorReason 
                INTEGER, 
            eMACRingInitializationsInitiated 
                Counter, 
            eMACRingInitializationsReceived 
                Counter, 
            eMACRingBeaconingInitiated 
                Counter, 
            eMACDuplicateAddressTestFailures 
                Counter, 
            eMACDuplicateTokensDetected 
                Counter, 
            eMACUpstreamNbrDuplAddressFlag 
                INTEGER, 
            eMACTracesInitiated 
 
 
                Counter, 
            eMACRestrictedTokenTimeout 
                INTEGER, 
            eMACFrameStatusErrors 
                Counter, 
            eMACFrameAlignmentErrors 
                Counter, 
            eMACTransmitUnderruns 
                Counter, 
            eMACRingLatency 
                INTEGER 
                 } 
 
    eMACSMTIndex OBJECT-TYPE 
        SYNTAX  INTEGER 
        ACCESS  read-only 
        STATUS  mandatory 
        DESCRIPTION 
               "The value of the SMT index associated with this MAC. 
               The value of this object is the same as the 
               snmpFddiMACSMTIndex, defined in the FDDI MIB, for this 
               MAC entity." 
        ::= { efddiMACEntry 1 } 
 
    eMACIndex OBJECT-TYPE 
        SYNTAX  INTEGER 
        ACCESS  read-only 
        STATUS  mandatory 
        DESCRIPTION 
               "Identifies the MAC Index.  The value of this object is 
               the same as the snmpFddiMACIndex, defined in the FDDI MIB, 
               for this MAC entity." 
        ::= { efddiMACEntry 2 } 
 
    eMACLinkIndex OBJECT-TYPE 
        SYNTAX  INTEGER 
        ACCESS  read-only 
        STATUS  mandatory 
        DESCRIPTION 
               "The SMT Resource Index." 
        ::= { efddiMACEntry 3 } 
 
    eMACLinkState OBJECT-TYPE 
        SYNTAX  INTEGER { 
 
 
                           offMaint(1), 
                           offReady(2), 
                           offFaultRecovery(3), 
                           onRingInit(4), 
                           onRingRun(5), 
                           broken(6) 
                        } 
        ACCESS  read-only 
        STATUS  mandatory 
        DESCRIPTION 
               "The current state of the link." 
        ::= { efddiMACEntry 4 } 
 
    eMACRingPurgerState OBJECT-TYPE 
        SYNTAX  INTEGER { 
                           purgerOff(1), 
                           candidate(2), 
                           nonPurger(3), 
                           purger(4) 
                        } 
        ACCESS  read-only 
        STATUS  mandatory 
        DESCRIPTION 
               "The current Ring Purger state." 
        ::= { efddiMACEntry 5 } 
 
    eMACRingPurgerEnable OBJECT-TYPE 
        SYNTAX  INTEGER { 
                           true(1), 
                           false(2) 
                        } 
        ACCESS  read-write 
        STATUS  mandatory 
        DESCRIPTION 
               "If true, this Link will participate in the Ring Purger 
               Election and, if elected, perform the Ring Purger function." 
        ::= { efddiMACEntry 6 } 
 
    eMACRingPurgeErrors OBJECT-TYPE 
        SYNTAX  Counter 
        ACCESS  read-only 
        STATUS  mandatory 
        DESCRIPTION 
               "The number of times the MAC PurgeError Event bit was set." 
        ::= { efddiMACEntry 7 } 
 
 
    eMACFrameStripMode OBJECT-TYPE 
        SYNTAX  INTEGER { 
                           saMatch(1), 
                           bridgeStrip(2) 
                        } 
        ACCESS  read-only 
        STATUS  mandatory 
        DESCRIPTION 
               "Method of frame removal used by this station." 
        ::= { efddiMACEntry 8 } 
 
    eMACFCIStripErrors OBJECT-TYPE 
        SYNTAX  Counter 
        ACCESS  read-only 
        STATUS  mandatory 
        DESCRIPTION 
               "The number of times a Frame Content Independent Strip 
               operation was terminated by receipt of a token." 
        ::= { efddiMACEntry 9 } 
 
    eMACRingErrorReason OBJECT-TYPE 
        SYNTAX  INTEGER { 
                           noReason(1), 
                           ringInitInitiated(6), 
                           ringInitReceived(7), 
                           ringBeaconingInitiated(8), 
                           daDetected(9), 
                           duplicateTokenDetected(10), 
                           ringPurgeError(11), 
                           bridgeStripError(12), 
                           ringOpOscillation(13), 
                           directedBeaconReceived(14), 
                           pcTraceInitiated(15), 
                           pcTraceReceived(16) 
                        } 
        ACCESS  read-only 
        STATUS  mandatory 
        DESCRIPTION 
               "Reason for last ring disturbance." 
        ::= { efddiMACEntry 10 } 
 
    eMACRingInitializationsInitiated OBJECT-TYPE 
        SYNTAX  Counter 
        ACCESS  read-only 
 
 
        STATUS  mandatory 
        DESCRIPTION 
               "Number of Ring Claim Processes initiated by this link 
               entity." 
        ::= { efddiMACEntry 11 } 
 
    eMACRingInitializationsReceived OBJECT-TYPE 
        SYNTAX  Counter 
        ACCESS  read-only 
        STATUS  mandatory 
        DESCRIPTION 
               "Number of Ring Claim Processes or Ring Beaconing Processes 
               initiated by a remote link entity and detected by this link 
               entity." 
        ::= { efddiMACEntry 12 } 
 
    eMACRingBeaconingInitiated OBJECT-TYPE 
        SYNTAX  Counter 
        ACCESS  read-only 
        STATUS  mandatory 
        DESCRIPTION 
               "The number of Ring Beacon Processes initiated by this 
               link entity." 
        ::= { efddiMACEntry 13 } 
 
    eMACDuplicateAddressTestFailures OBJECT-TYPE 
        SYNTAX  Counter 
        ACCESS  read-only 
        STATUS  mandatory 
        DESCRIPTION 
               "The number of times the duplicate address test failed." 
        ::= { efddiMACEntry 14 } 
 
    eMACDuplicateTokensDetected OBJECT-TYPE 
        SYNTAX  Counter 
        ACCESS  read-only 
        STATUS  mandatory 
        DESCRIPTION 
               "The number of times this link entity detected a duplicate 
               token." 
        ::= { efddiMACEntry 15 } 
 
    eMACUpstreamNbrDuplAddressFlag OBJECT-TYPE 
        SYNTAX  INTEGER { 
                           true(1), 
 
 
                           false(2), 
                           unknown(3) 
                        } 
        ACCESS  read-only 
        STATUS  mandatory 
        DESCRIPTION 
               "The upstream neighbor's duplicate address status, as 
               reported by the NIF frame.  Unknown if no NIF frame has 
               been received yet." 
        ::= { efddiMACEntry 16 } 
 
    eMACTracesInitiated OBJECT-TYPE 
        SYNTAX  Counter 
        ACCESS  read-only 
        STATUS  mandatory 
        DESCRIPTION 
               "The number of PC Traces initiated by this station." 
        ::= { efddiMACEntry 17 } 
 
    eMACRestrictedTokenTimeout OBJECT-TYPE 
        SYNTAX  INTEGER 
        ACCESS  read-write 
        STATUS  mandatory 
        DESCRIPTION 
               "The restricted token timeout, which limits how long a 
               single restricted mode dialog may last before being 
               terminated." 
        ::= { efddiMACEntry 18 } 
 
    eMACFrameStatusErrors OBJECT-TYPE 
        SYNTAX  Counter 
        ACCESS  read-only 
        STATUS  mandatory 
        DESCRIPTION 
               "The number of frames received on the line that had the 
               E (error detected) indicator set or a missing E indicator." 
        ::= { efddiMACEntry 19 } 
 
    eMACFrameAlignmentErrors OBJECT-TYPE 
        SYNTAX  Counter 
        ACCESS  read-only 
        STATUS  mandatory 
        DESCRIPTION 
               "The number of frames received on the line that contained 
               an odd number of symbols; that is, a non-integral number 
               of octets." 
        ::= { efddiMACEntry 20 } 
 
    eMACTransmitUnderruns OBJECT-TYPE 
        SYNTAX  Counter 
        ACCESS  read-only 
        STATUS  mandatory 
        DESCRIPTION 
               "The number of times an underrun occured because the 
               device's transmit FIFO became empty due to insufficient 
               memory.  In other words, the device was trying to 
               transmit but could not get into memory fast enough." 
        ::= { efddiMACEntry 21 } 
 
    eMACRingLatency OBJECT-TYPE 
        SYNTAX  INTEGER 
        ACCESS  read-only 
        STATUS  mandatory 
        DESCRIPTION 
               "The total ring latency in 1 nanosecond units, as measured 
               by the amount of time that it takes to receive back a void 
               frame transmitted by the MAC chip.  Note that implementations 
               that do not have the capability to measure the ring latency 
               will not return this object." 
        ::= { efddiMACEntry 22 } 
 
    -- efddiPORTTable  - the extended PORT table 
    -- these are objects implemented in Digital implementations over 
    -- and above the standard PORT group in the IETF FDDI MIB. 
 
    efddiPORTTable OBJECT-TYPE 
        SYNTAX  SEQUENCE OF EfddiPORTEntry 
        ACCESS  not-accessible 
        STATUS  mandatory 
        DESCRIPTION 
               "A list of PORT entries.  The number of entries is given 
               by portNumber, defined in the FDDI MIB." 
        ::= { efddiPORT 1 } 
 
    efddiPORTEntry OBJECT-TYPE 
        SYNTAX  EfddiPORTEntry 
        ACCESS  not-accessible 
        STATUS  mandatory 
        DESCRIPTION 
 
 
               "A collection of objects containing information for a 
               given PORT entity." 
        INDEX  { ePORTSMTIndex, ePORTIndex } 
        ::= { efddiPORTTable 1 } 
 
    EfddiPORTEntry ::= 
        SEQUENCE { 
            ePORTSMTIndex 
                INTEGER, 
            ePORTIndex 
                INTEGER, 
            ePORTPHYIndex 
                INTEGER, 
            ePORTPMDType 
                INTEGER, 
            ePORTPHYState 
                INTEGER, 
            ePORTRejectReason 
                INTEGER, 
            ePORTConnectionsCompleted 
                Counter, 
            ePORTTNEExpRejects 
                Counter, 
            ePORTElasticityBufferErrors 
                Counter 
                 } 
 
    ePORTSMTIndex OBJECT-TYPE 
        SYNTAX  INTEGER 
        ACCESS  read-only 
        STATUS  mandatory 
        DESCRIPTION 
               "The value of the SMT index associated with this port. 
               The value of this object is the same as the 
               snmpFddiPORTSMTIndex, defined in the FDDI MIB, for 
               this PORT entity." 
        ::= { efddiPORTEntry 1 } 
 
    ePORTIndex OBJECT-TYPE 
        SYNTAX  INTEGER 
        ACCESS  read-only 
        STATUS  mandatory 
        DESCRIPTION 
               "Identifies the PORT Index.  The value of this object is 
               the same as the snmpFddiPORTIndex, defined in the FDDI MIB, 
 
 
               for this PORT entity." 
        ::= { efddiPORTEntry 2 } 
 
    ePORTPHYIndex OBJECT-TYPE 
        SYNTAX  INTEGER 
        ACCESS  read-only 
        STATUS  mandatory 
        DESCRIPTION 
               "The SMT Resource index.  Index of the PHY resource 
               used to identify the PHY PORT in ANSI SMT frames." 
        ::= { efddiPORTEntry 3 } 
 
    ePORTPMDType OBJECT-TYPE 
        SYNTAX  INTEGER { 
                           pmdNone(1), 
                           pmdMM(2), 
                           pmdSM(3), 
                           pmdLC(4), 
                           pmdTHN(5), 
                           pmdSTP(6), 
                           pmdUTP(7) 
                        } 
        ACCESS  read-only 
        STATUS  mandatory 
        DESCRIPTION 
               "The physical media type of the PORT." 
        ::= { efddiPORTEntry 4 } 
 
    ePORTPHYState OBJECT-TYPE 
        SYNTAX  INTEGER { 
                           offmaintenance(1), 
                           broken(2), 
                           offready(3), 
                           wait(4), 
                           starting(5), 
                           failed(6), 
                           watch(7), 
                           inuse(8) 
                        } 
        ACCESS  read-only 
        STATUS  mandatory 
        DESCRIPTION 
               "The PHY state." 
        ::= { efddiPORTEntry 5 } 
 
 
    ePORTRejectReason OBJECT-TYPE 
        SYNTAX  INTEGER { 
                           noReason(1), 
                           lctLocal(2), 
                           lctRemote(3), 
                           lctBoth(4), 
                           lemFailure(5), 
                           topologyRules(6), 
                           tneExpired(7), 
                           remoteReject(8), 
                           tracesInProgress(9), 
                           tracesReceived(10), 
                           standby(11), 
                           lctProtocol(12) 
                        } 
        ACCESS  read-only 
        STATUS  mandatory 
        DESCRIPTION 
               "The current reject reason." 
        ::= { efddiPORTEntry 6 } 
 
    ePORTConnectionsCompleted OBJECT-TYPE 
        SYNTAX  Counter 
        ACCESS  read-only 
        STATUS  mandatory 
        DESCRIPTION 
               "The number of Physical Connections established for this 
               PHY PORT." 
        ::= { efddiPORTEntry 7 } 
 
    ePORTTNEExpRejects OBJECT-TYPE 
        SYNTAX  Counter 
        ACCESS  read-only 
        STATUS  mandatory 
        DESCRIPTION 
               "The number of times a physical disconnection took place 
               because the TNE Noise Timer expired." 
        ::= { efddiPORTEntry 8 } 
 
    ePORTElasticityBufferErrors OBJECT-TYPE 
        SYNTAX  Counter 
        ACCESS  read-only 
        STATUS  mandatory 
        DESCRIPTION 
               "The number of ELM Chip EBUFF_ERROR events." 
 
 
        ::= { efddiPORTEntry 9 } 
 
    -- 
    -- FDDI FDX (full-duplex) objects 
    -- 
    -- This is part of the MAC object.  However this is an optional group 
    -- to be implemented only for full-duplex FDDI links. 
    -- 
 
    efddiFDXTable OBJECT-TYPE 
        SYNTAX  SEQUENCE OF EfddiFDXEntry 
        ACCESS  not-accessible 
        STATUS  mandatory 
        DESCRIPTION 
               "A list of FDX entries." 
        ::= { efddiFDX 1 } 
 
    efddiFDXEntry OBJECT-TYPE 
        SYNTAX  EfddiFDXEntry 
        ACCESS  not-accessible 
        STATUS  mandatory 
        DESCRIPTION 
               "A collection of objects containing information for a 
               given FDX MAC entity." 
        INDEX  { eFDXSMTIndex, eFDXMACIndex } 
        ::= { efddiFDXTable 1 } 
 
    EfddiFDXEntry ::= 
        SEQUENCE { 
            eFDXSMTIndex 
                INTEGER, 
            eFDXMACIndex 
                INTEGER, 
            eFDXEnable 
                INTEGER, 
            eFDXOp 
                INTEGER, 
            eFDXState 
                INTEGER 
                 } 
 
    eFDXSMTIndex OBJECT-TYPE 
        SYNTAX  INTEGER 
        ACCESS  read-only 
 
 
        STATUS  mandatory 
        DESCRIPTION 
               "The value of the SMT index associated with this FDX MAC." 
        ::= { efddiFDXEntry 1 } 
 
    eFDXMACIndex OBJECT-TYPE 
        SYNTAX  INTEGER 
        ACCESS  read-only 
        STATUS  mandatory 
        DESCRIPTION 
               "The value of the MAC index associated with this FDX MAC." 
        ::= { efddiFDXEntry 2 } 
 
    eFDXEnable OBJECT-TYPE 
        SYNTAX  INTEGER { 
                          true(1), 
                          false(2) 
                        } 
        ACCESS  read-write 
        STATUS  mandatory 
        DESCRIPTION 
               "When true, this link will participate in the full duplex 
               auto-configuration and, if this is successful, will 
               operate in the full duplex mode." 
        ::= { efddiFDXEntry 3 } 
 
    eFDXOp OBJECT-TYPE 
        SYNTAX  INTEGER { 
                          true(1), 
                          false(2) 
                        } 
        ACCESS  read-only 
        STATUS  mandatory 
        DESCRIPTION 
               "When true, this link is operating in the full duplex mode." 
        ::= { efddiFDXEntry 4 } 
 
    eFDXState OBJECT-TYPE 
        SYNTAX  INTEGER { 
                          fdxIdle(1), 
                          fdxRequest(2), 
                          fdxConfirm(3), 
                          fdxOperation(4) 
                        } 
        ACCESS  read-only 
 
 
        STATUS  mandatory 
        DESCRIPTION 
               "The state of the full duplex Control process." 
        ::= { efddiFDXEntry 5 } 
 
 
    -- 
    -- esystem   - groups in the extended system module 
    -- 
    -- these are system objects implemented in Digital bridges and 
    -- concentrators. 
    -- 
 
    esysChar       OBJECT IDENTIFIER ::= { esystem 1 } 
    esysStatus     OBJECT IDENTIFIER ::= { esystem 2 } 
    esysCounters   OBJECT IDENTIFIER ::= { esystem 3 } 
    esysConcConfig OBJECT IDENTIFIER ::= { esystem 4 } 
 
    -- esysChar  - the system Characteristics group 
    -- this group consists of information about the device's hardware 
    -- and firmware.  It also displays information about hardware and 
    -- software switches that contrrol device operation. 
 
    esysRomVersion OBJECT-TYPE 
        SYNTAX  INTEGER 
        ACCESS  read-only 
        STATUS  mandatory 
        DESCRIPTION 
               "The version number of the software stored in ROM." 
        ::= { esysChar 1 } 
 
    esysInitSwitch OBJECT-TYPE 
        SYNTAX  INTEGER { 
                           other(1), 
                           reset(2), 
                           resetWithDefaults(3) 
                        } 
        ACCESS  read-write 
        STATUS  mandatory 
        DESCRIPTION 
               "This object allows the management action of initializing 
               a device and forcing it to run selftest.  It can also be 
               used to reset all information added to the device's NVRAM. 
               When read, it returns a value of other(1)." 
        ::= { esysChar 2 } 
 
    esysResetDefaultsSwitch OBJECT-TYPE 
        SYNTAX  INTEGER { 
                           true(1), 
                           false(2) 
 
 
                        } 
        ACCESS  read-only 
        STATUS  mandatory 
        DESCRIPTION 
               "This object is the state of a hardware switch which, 
               when true, causes the device to reset its parameters 
               to the factory defaults when initialized." 
        ::= { esysChar 3 } 
 
    esysGatewayAddress OBJECT-TYPE 
        SYNTAX  IpAddress 
        ACCESS  read-write 
        STATUS  mandatory 
        DESCRIPTION 
               "This object allows the setting of a default gateway 
               address for this device." 
        ::= { esysChar 4 } 
 
    esysTrapAddressTable OBJECT-TYPE 
        SYNTAX  SEQUENCE OF EsysTrapEntry 
        ACCESS  not-accessible 
        STATUS  mandatory 
        DESCRIPTION 
               "A table of IP Addresses to which this device will send 
               traps." 
        ::= { esysChar 5 } 
 
    esysTrapEntry OBJECT-TYPE 
        SYNTAX  EsysTrapEntry 
        ACCESS  not-accessible 
        STATUS  mandatory 
        DESCRIPTION 
               "Each entry contains an IP Address to which all SNMP Traps 
               will be sent by this device." 
        INDEX   { esysTrapAddress } 
        ::= { esysTrapAddressTable 1 } 
 
    EsysTrapEntry ::= 
        SEQUENCE { 
            esysTrapAddress 
                IpAddress 
                 } 
 
    esysTrapAddress OBJECT-TYPE 
 
 
        SYNTAX  IpAddress 
        ACCESS  read-write 
        STATUS  mandatory 
        DESCRIPTION 
               "An IP Address to which all SNMP traps generated by this 
               device will be sent." 
        ::= { esysTrapEntry 1 } 
 
    esysUpdateSwitch OBJECT-TYPE 
        SYNTAX  INTEGER { 
                           true(1), 
                           false(2) 
                        } 
        ACCESS  read-write 
        STATUS  mandatory 
        DESCRIPTION 
               "A software switch that, when set to true, instructs the 
               device to accept a down-line loaded firmware upgrade. 
               If false, the device will not accept upgrades." 
        ::= { esysChar 6 } 
 
    esysLastLoadHost OBJECT-TYPE 
        SYNTAX  OCTET STRING (SIZE (6)) 
        ACCESS  read-only 
        STATUS  mandatory 
        DESCRIPTION 
               "The physical address of the last host, if any, that 
               responded to the device's request for a downline load 
               of software." 
        ::= { esysChar 7 } 
 
    -- esysStatus  - the system Status group 
    -- this group consists of operational status of the device. 
 
    esysDeviceState OBJECT-TYPE 
        SYNTAX  INTEGER { 
                           init(1), 
                           operate(2), 
                           broken(3) 
                        } 
        ACCESS  read-only 
        STATUS  mandatory 
        DESCRIPTION 
               "The operational state of the device." 
 
 
        ::= { esysStatus 1 } 
 
    esysDeviceBrokenReason OBJECT-TYPE 
        SYNTAX  INTEGER { 
                           none(1), 
                           selftestFail(2), 
                           onlineDiagFail(3), 
                           firmwareFail(4) 
                        } 
        ACCESS  read-only 
        STATUS  mandatory 
        DESCRIPTION 
               "The reason that the Device State is BROKEN.  If current 
               state is not BROKEN and the Unsolicited Resets counter is 
               nonzero, this object show reason for last failure." 
        ::= { esysStatus 2 } 
 
    esysNvramFailed OBJECT-TYPE 
        SYNTAX  INTEGER { 
                           true(1), 
                           false(2) 
                        } 
        ACCESS  read-only 
        STATUS  mandatory 
        DESCRIPTION 
               "A flag, that, when set to True, indicates that the 
               NVRAM failed selftest following the last initialization 
               of the device." 
        ::= { esysStatus 3 } 
 
    -- esysCounters  - the system Counter group 
    -- this group consists of counters that measure operational 
    -- events and errors. 
 
    esysPowerups OBJECT-TYPE 
        SYNTAX  Counter 
        ACCESS  read-only 
        STATUS  mandatory 
        DESCRIPTION 
               "The number of times this device was powered on. 
               Power Ups, Management Resets and Unsolicited Resets 
               are all mutually exclusive." 
        ::= { esysCounters 1 } 
 
 
    esysMgmtResets OBJECT-TYPE 
        SYNTAX  Counter 
        ACCESS  read-only 
        STATUS  mandatory 
        DESCRIPTION 
               "Number of times the device was initialized with a 
               management command using esysInitSwitch.  Power Ups, 
               Management Resets and Unsolicited Resets are all mutually 
               exclusive." 
        ::= { esysCounters 2 } 
 
    esysUnsolicitedResets OBJECT-TYPE 
        SYNTAX  Counter 
        ACCESS  read-only 
        STATUS  mandatory 
        DESCRIPTION 
               "Number of times the device initialized itself after 
               encountering a fatal error.  Power Ups, Management Resets 
               and Unsolicited Resets are all mutually exclusive." 
        ::= { esysCounters 3 } 
 
    -- 
    -- esysConcConfig   - Optional group, applicable only to 
    --                    FDDI Concentrator 
    -- 
    -- this group consists of a FRU (Field Replaceable Unit) Configuration 
    -- Table applicable to the FDDI concentrator, and a switch to enable 
    -- or disable port up/down traps. 
    -- 
 
    esysFRUConfigTable OBJECT-TYPE 
        SYNTAX  SEQUENCE OF EsysFRUConfigEntry 
        ACCESS  not-accessible 
        STATUS  mandatory 
        DESCRIPTION 
               "A list of configuration table entries." 
        ::= { esysConcConfig 1 } 
 
    esysFRUConfigEntry OBJECT-TYPE 
        SYNTAX  EsysFRUConfigEntry 
        ACCESS  not-accessible 
        STATUS  mandatory 
        DESCRIPTION 
               "A collection of objects containing information for a 
 
 
               given configuration entry." 
        INDEX  { esysFRUIndex } 
        ::= { esysFRUConfigTable 1 } 
 
    EsysFRUConfigEntry ::= 
        SEQUENCE { 
            esysFRUIndex 
                INTEGER, 
            esysFRUSlot 
                INTEGER, 
            esysFRUDesc 
                DisplayString, 
            esysFRUType 
                INTEGER, 
            esysFRURev 
                INTEGER, 
            esysFRUState 
                INTEGER 
                 } 
 
    esysFRUIndex OBJECT-TYPE 
        SYNTAX  INTEGER 
        ACCESS  read-only 
        STATUS  mandatory 
        DESCRIPTION 
               "This object is used for indexing the FRU configuration 
               table." 
        ::= { esysFRUConfigEntry 1 } 
 
    esysFRUSlot OBJECT-TYPE 
        SYNTAX  INTEGER 
        ACCESS  read-only 
        STATUS  mandatory 
        DESCRIPTION 
               "The physical slot number in which the module resides, if 
               applicable.  If not applicable, this is reported as '0'." 
        ::= { esysFRUConfigEntry 2 } 
 
    esysFRUDesc OBJECT-TYPE 
        SYNTAX  DisplayString 
        ACCESS  read-only 
        STATUS  mandatory 
        DESCRIPTION 
               "A textual description of this FRU." 
        ::= { esysFRUConfigEntry 3 } 
 
 
    esysFRUType OBJECT-TYPE 
        SYNTAX  INTEGER { 
                           empty(1), 
                           ansiMgmtCard(2), 
                           ansiPortCard4line(3), 
                           fan(4), 
                           apCard(5), 
                           niCard(6), 
                           fddiCard(7), 
                           controllerBackplane(8), 
                           qmCard(9), 
                           lowPowerPortCard4line(10), 
                           singleModeAnsiPortCard4line(11), 
                           thinwirePortCard6line(12), 
                           lowPowerPortCard6line(13), 
                           stpCopperPortCard6line(14), 
                           singleModeMgmtCard(15), 
                           ansi-SingleModeMgmtCard(16), 
                           singleMode-ANSIMgmtCard(17), 
                           upgradeApCard(19), 
                           threeNiCard(20), 
                           dasAnsiFddiCard(21), 
                           dasAnsiASingleModeBfiCard(22), 
                           dasSingleModeAAnsiBfiCard(23), 
                           dasSingleModeFddiCard(24), 
                           sasSingleModeFddiCard(25), 
                           opticalBypass(26), 
                           obmUartCard(27), 
                           ansiPortCard6line(29) 
                        } 
        ACCESS  read-only 
        STATUS  mandatory 
        DESCRIPTION 
               "Integer representation for the FRU type.  This is the 
               machine-readable form of the descriptor object." 
        ::= { esysFRUConfigEntry 4 } 
 
    esysFRURev OBJECT-TYPE 
        SYNTAX  INTEGER 
        ACCESS  read-only 
        STATUS  mandatory 
        DESCRIPTION 
               "This object represents the FRU revision number." 
        ::= { esysFRUConfigEntry 5 } 
 
 
    esysFRUState OBJECT-TYPE 
        SYNTAX  INTEGER { 
                           empty(1),       -- no FRU present in this slot 
                           working(2),     -- FRU is working 
                           marginal(3),    -- FRU is marginal 
                           broken(4),      -- FRU is broken 
                           obrNotSupported(5) -- only for optical bypass card 
                        } 
        ACCESS  read-only 
        STATUS  mandatory 
        DESCRIPTION 
               "The operational state of the FRU, if present." 
        ::= { esysFRUConfigEntry 6 } 
 
    esysFddiPortTrapSwitch OBJECT-TYPE 
        SYNTAX  INTEGER { 
                           true(1), 
                           false(2) 
                        } 
        ACCESS  read-write 
        STATUS  mandatory 
        DESCRIPTION 
               "This is a switch to enable or diable FDDI port up and port 
               down traps.  When set to true, the concentrator will 
               send a trap when one of its ports comes up or goes down." 
        ::= { esysConcConfig 2 } 
 
 
    -- 
    -- eifTable   - groups in the extended interface module 
    -- 
    -- these are interface objects implemented in Digital bridges and 
    -- concentrators, over and above what is available via MIB-II. 
    -- 
 
    eifTable OBJECT-TYPE 
        SYNTAX  SEQUENCE OF EifEntry 
        ACCESS  not-accessible 
        STATUS  mandatory 
        DESCRIPTION 
               "A list of interface entries.  The number of entries is 
               given by ifNumber, defined in MIB-II." 
        ::= { einterfaces 1 } 
 
    eifEntry OBJECT-TYPE 
        SYNTAX  EifEntry 
        ACCESS  not-accessible 
        STATUS  mandatory 
        DESCRIPTION 
               "A collection of objects containing information for a 
               given interface." 
        INDEX  { eifIndex } 
        ::= { eifTable 1 } 
 
    EifEntry ::= 
        SEQUENCE { 
            eifIndex 
                INTEGER, 
            eifBadFramesReceived 
                Counter, 
            eifReceiveOverrun 
                Counter, 
            eifOversizeFrames 
                Counter, 
            eifTransmitFramesError 
                Counter, 
            eifMgmtSetsAllowedSwitch 
                INTEGER 
                 } 
 
    eifIndex OBJECT-TYPE 
        SYNTAX  INTEGER 
        ACCESS  read-only 
 
 
        STATUS  mandatory 
        DESCRIPTION 
               "Identifies the Interface.  The value of this object is 
               the same as the ifIndex, defined in MIB-II, for this 
               interface." 
        ::= { eifEntry 1 } 
 
    eifBadFramesReceived OBJECT-TYPE 
        SYNTAX  Counter 
        ACCESS  read-only 
        STATUS  mandatory 
        DESCRIPTION 
               "Number of frames received with a bad frame check sequence." 
        ::= { eifEntry 2 } 
 
    eifReceiveOverrun OBJECT-TYPE 
        SYNTAX  Counter 
        ACCESS  read-only 
        STATUS  mandatory 
        DESCRIPTION 
               "Number of times that the device received a frame loss 
               indication from the hardware on the interface." 
        ::= { eifEntry 3 } 
 
    eifOversizeFrames OBJECT-TYPE 
        SYNTAX  Counter 
        ACCESS  read-only 
        STATUS  mandatory 
        DESCRIPTION 
               "Number of frames received on the interface that were 
               larger than the maximum legal size." 
        ::= { eifEntry 4 } 
 
    eifTransmitFramesError OBJECT-TYPE 
        SYNTAX  Counter 
        ACCESS  read-only 
        STATUS  mandatory 
        DESCRIPTION 
               "Number of frames that were transmitted with an error 
               on the line." 
        ::= { eifEntry 5 } 
 
    eifMgmtSetsAllowedSwitch OBJECT-TYPE 
        SYNTAX  INTEGER { 
                           true(1), 
 
 
                           false(2) 
                        } 
        ACCESS  read-only 
        STATUS  mandatory 
        DESCRIPTION 
               "This hardware switch, when true, allows write 
               access to the device.  This object has meaning only 
               when the corresponding functionality is present." 
        ::= { eifEntry 6 } 
 
 
    -- 
    -- ebridge   - groups in the extended bridge module 
    -- 
    -- these are bridge objects implemented in Digital bridges 
    -- over and above what is required by the Bridge MIB 
    -- 
 
    ebrChar             OBJECT IDENTIFIER ::= { ebridge 1 } 
    ebrStat             OBJECT IDENTIFIER ::= { ebridge 2 } 
    ebrCoun             OBJECT IDENTIFIER ::= { ebridge 3 } 
    ebrSpan             OBJECT IDENTIFIER ::= { ebridge 4 } 
    ebrInterfaces       OBJECT IDENTIFIER ::= { ebridge 5 } 
    ebrTwoPortStatic    OBJECT IDENTIFIER ::= { ebridge 6 } 
    ebrMultiPortStatic  OBJECT IDENTIFIER ::= { ebridge 7 } 
    ebrTwoProtoFilt     OBJECT IDENTIFIER ::= { ebridge 8 } 
    ebrMultiProtoFilt   OBJECT IDENTIFIER ::= { ebridge 9 } 
    ebrMultiFiltSw      OBJECT IDENTIFIER ::= { ebridge 10 } 
    ebrNTP              OBJECT IDENTIFIER ::= { ebridge 11 } 
    ebrRateLimiting     OBJECT IDENTIFIER ::= { ebridge 12 } 
    ebrSpanTurnOff      OBJECT IDENTIFIER ::= { ebridge 13 } 
 
    -- ebrChar  - the Bridge Characteristics group 
    -- this group consists of information about the bridge's hardware 
    -- and firmware.  It also displays information about hardware and 
    -- software switches that contrrol device operation. 
 
    ebrLB100SpanningTreeVer OBJECT-TYPE 
        SYNTAX  INTEGER 
        ACCESS  read-only 
        STATUS  mandatory 
        DESCRIPTION 
               "The version number of the Spanning Tree algorithm 
               used by the bridge when in the LAN Bridge 100 Spanning 
               Tree mode." 
        ::= { ebrChar 1 } 
 
    ebr802SpanningTreeVer OBJECT-TYPE 
        SYNTAX  INTEGER 
        ACCESS  read-only 
        STATUS  mandatory 
        DESCRIPTION 
               "The version number of the Spanning Tree algorithm 
               used by the bridge when in the 802.1d Spanning Tree mode." 
        ::= { ebrChar 2 } 
 
 
    ebrMaxForwardingDBEntries OBJECT-TYPE 
        SYNTAX  INTEGER 
        ACCESS  read-only 
        STATUS  mandatory 
        DESCRIPTION 
               "The maximum number of address entries that the bridge 
               can store in its volatile memory." 
        ::= { ebrChar 3 } 
 
    ebrMaxNVForwardingDBEntries OBJECT-TYPE 
        SYNTAX  INTEGER 
        ACCESS  read-only 
        STATUS  mandatory 
        DESCRIPTION 
               "The maximum number of permanent address entries that 
               the bridge canstore in its NVRAM." 
        ::= { ebrChar 4 } 
 
    ebrMaxProtocolDBEntries OBJECT-TYPE 
        SYNTAX  INTEGER 
        ACCESS  read-only 
        STATUS  mandatory 
        DESCRIPTION 
               "The maximum number of protocol entries that the bridge 
               can store in its protocol database.  These entries control 
               the handling of frames based on their Ethernet PT, 
               IEEE 802.2 DSAP or IEEE 802 SNAP Protocol ID." 
        ::= { ebrChar 5 } 
 
    ebrMaxNVProtocolDBEntries OBJECT-TYPE 
        SYNTAX  INTEGER 
        ACCESS  read-only 
        STATUS  mandatory 
        DESCRIPTION 
               "The maximum number of protocol entries that the bridge 
               can store in its nonvolatile memory.  These are retained 
               after a power-down." 
    ::= { ebrChar 6 } 
 
    ebrForwardingDBPurgeThreshold OBJECT-TYPE 
        SYNTAX  INTEGER 
        ACCESS  read-only 
        STATUS  mandatory 
        DESCRIPTION 
               "The total number of active and inactive address entries 
 
 
               that will trigger a purge of the inactive entries." 
        ::= { ebrChar 7 } 
 
    ebrPortTestPassedThreshold OBJECT-TYPE 
        SYNTAX  INTEGER 
        ACCESS  read-write 
        STATUS  mandatory 
        DESCRIPTION 
               "The number of consecutive successful self-tests needed 
               before the bridge considers a line to be operational." 
        ::= { ebrChar 8 } 
 
    ebrPortTestInterval OBJECT-TYPE 
        SYNTAX  INTEGER 
        ACCESS  read-write 
        STATUS  mandatory 
        DESCRIPTION 
               "The interval, in seconds, at which the bridge will run 
               selftests on a line that is in the BROKEN state." 
        ::= { ebrChar 9 } 
 
    ebrTopologyChangeTimer OBJECT-TYPE 
        SYNTAX  INTEGER 
        ACCESS  read-only 
        STATUS  mandatory 
        DESCRIPTION 
               "The number of seconds remaining, if this is the Root, 
               for which Topology Change will be propagated in Hello 
               messages.  Otherwise this value will be reported as 0." 
        ::= { ebrChar 10 } 
 
    ebrManualFilterSwitch OBJECT-TYPE 
        SYNTAX  INTEGER { 
                           true(1), 
                           false(2) 
                        } 
        ACCESS  read-write 
        STATUS  mandatory 
        DESCRIPTION 
               "A switch that controls address filtering.  When true, 
               the bridge purges the learned entries from its forwarding 
               database, stops its learning process, and forwards only 
               frames with destination and source addresses that have 
               been specified via management." 
        ::= { ebrChar 11 } 
 
 
    ebrFragmentationSwitch OBJECT-TYPE 
        SYNTAX  INTEGER { 
                           true(1), 
                           false(2) 
                        } 
        ACCESS  read-write 
        STATUS  mandatory 
        DESCRIPTION 
               "A switch that controls whether fragmentation is performed 
               by the bridge when a large IP frame is received on a datalink 
               that supports a higer frame size than the other datalink." 
        ::= { ebrChar 12 } 
 
    ebrRemoveMgmtAddress OBJECT-TYPE 
        SYNTAX  INTEGER { 
                           other(1), 
                           true(2) 
                        } 
        ACCESS  read-write 
        STATUS  mandatory 
        DESCRIPTION 
               "This object allows the action of removing all management 
               entered addresses from the forwarding database when 
               set to true(2).  When read, it returns a value of other(1)." 
        ::= { ebrChar 13 } 
 
    ebrRemoveMgmtProto OBJECT-TYPE 
        SYNTAX  INTEGER { 
                           other(1), 
                           true(2) 
                        } 
        ACCESS  read-write 
        STATUS  mandatory 
        DESCRIPTION 
               "This object allows the action of removing all management 
               entered protocols from the protocol database when set 
               to true(2).  When read, it returns a value of other(1)." 
        ::= { ebrChar 14 } 
 
    -- ebrStat  - the Bridge Status group 
    -- this group consists of operational status of the bridge. 
 
    ebrCurrForwardingDBEntries OBJECT-TYPE 
 
 
        SYNTAX  INTEGER 
        ACCESS  read-only 
        STATUS  mandatory 
        DESCRIPTION 
               "The number of address entries in the bridge's volatile 
               memory.  These will be lost upon loss of power." 
        ::= { ebrStat 1 } 
 
    ebrCurrNVForwardingDBEntries OBJECT-TYPE 
        SYNTAX  INTEGER 
        ACCESS  read-only 
        STATUS  mandatory 
        DESCRIPTION 
               "The number of address entries in the bridge's NVRAM. 
               These will be retained after loss of power." 
        ::= { ebrStat 2 } 
 
    ebrCurrProtocolDBEntries OBJECT-TYPE 
        SYNTAX  INTEGER 
        ACCESS  read-only 
        STATUS  mandatory 
        DESCRIPTION 
               "The number of protocol entries that are stored in the 
               bridge's protocol database.  These control the handling 
               of frames based on their Ethernet protocol type, IEEE 
               802.2 DSAP, or 802 SNAP Protocol ID." 
        ::= { ebrStat 3 } 
 
    ebrCurrNVProtocolDBEntries OBJECT-TYPE 
        SYNTAX  INTEGER 
        ACCESS  read-only 
        STATUS  mandatory 
        DESCRIPTION 
               "The number of protocol entries in the bridge's NVRAM. 
               These are retained after a power loss." 
        ::= { ebrStat 4 } 
 
    ebrMgmtHeardPort OBJECT-TYPE 
        SYNTAX  INTEGER 
        ACCESS  read-only 
        STATUS  mandatory 
        DESCRIPTION 
               "The port on which this command was received." 
        ::= { ebrStat 5 } 
 
 
    ebrLB100BeingPolled OBJECT-TYPE 
        SYNTAX  OCTET STRING (SIZE (6)) 
        ACCESS  read-only 
        STATUS  mandatory 
        DESCRIPTION 
               "The address of the LAN Bridge 100 mode bridge that sent 
               this bridge into the LAN Bridge 100 Spanning Tree mode. 
               If this bridge is the Root, this object indicates the 
               bridge that will be polled periodically to determine 
               if it is still necessary to stay in this Spanning Tree 
               mode." 
        ::= { ebrStat 6 } 
 
    ebrInactiveForwardingDBEntries OBJECT-TYPE 
        SYNTAX  INTEGER 
        ACCESS  read-only 
        STATUS  mandatory 
        DESCRIPTION 
               "The number of inactive address entries in the bridge's 
               forwarding database.  The bridge marks an address entry 
               inactive when the entry is aged out." 
        ::= { ebrStat 7 } 
 
    ebrTimeSinceForwardingDBPurged OBJECT-TYPE 
        SYNTAX  INTEGER 
        ACCESS  read-only 
        STATUS  mandatory 
        DESCRIPTION 
               "The number of seconds since the bridge cleared the 
               forwarding database of inactive entries." 
        ::= { ebrStat 8 } 
 
    ebrTimeSinceLastHello OBJECT-TYPE 
        SYNTAX  INTEGER 
        ACCESS  read-only 
        STATUS  mandatory 
        DESCRIPTION 
               "The number of seconds since the bridge last sent a 
               Hello message." 
        ::= { ebrStat 9 } 
 
    -- ebrCoun  - the Bridge Counters group 
    -- this group consists of counters that measure operational 
    -- events and errors. 
 
 
    ebrDeviceFramesLost OBJECT-TYPE 
        SYNTAX  Counter 
        ACCESS  read-only 
        STATUS  mandatory 
        DESCRIPTION 
               "The number of frames addressed to the bridge itself that 
               the bridge discarded because it did not have sufficient 
               receive buffers available." 
        ::= { ebrCoun 1 } 
 
    ebrSpanningTreeModeChanges OBJECT-TYPE 
        SYNTAX  Counter 
        ACCESS  read-only 
        STATUS  mandatory 
        DESCRIPTION 
               "The number of times that the bridge switched from the 
               802.1d Spanning Tree mode to the LB100 Spanning Tree mode." 
        ::= { ebrCoun 2 } 
 
    -- ebrSpan  - the Bridge Spanning Tree group 
    -- this group consists of Spanning Tree characteristics over and 
    -- above what is required by the Bridge MIB. 
 
    ebrBestRootAge OBJECT-TYPE 
        SYNTAX  INTEGER 
        ACCESS  read-only 
        STATUS  mandatory 
        DESCRIPTION 
               "The age, in hundereths of seconds, of the Hello message 
               that established the best root." 
        ::= { ebrSpan 1 } 
 
    ebrTopologyChangeFlag OBJECT-TYPE 
        SYNTAX  INTEGER { 
                           true(1), 
                           false(2) 
                        } 
        ACCESS  read-only 
        STATUS  mandatory 
        DESCRIPTION 
               "A flag that indicates whether a Topology Change is 
               currently in effect on the extended LAN." 
        ::= { ebrSpan 2 } 
 
 
    ebrTellParentFlag OBJECT-TYPE 
        SYNTAX  INTEGER { 
                           true(1), 
                           false(2) 
                        } 
        ACCESS  read-only 
        STATUS  mandatory 
        DESCRIPTION 
               "A flag that indicates if the bridge is attempting to 
               propagate a topology change towards the Root." 
        ::= { ebrSpan 3 } 
 
    ebrForwardingDBShortAgingTime OBJECT-TYPE 
        SYNTAX  INTEGER 
        ACCESS  read-write 
        STATUS  mandatory 
        DESCRIPTION 
               "The number of seconds that the bridge keeps learned 
               entries active while a topology change is in effect." 
        ::= { ebrSpan 4 } 
 
    ebrBadHelloLimit OBJECT-TYPE 
        SYNTAX  INTEGER 
        ACCESS  read-write 
        STATUS  mandatory 
        DESCRIPTION 
               "The number of hello intervals during which the bridge 
               receives one or more bad hellos on a line, before the 
               bridge performs a test on the link.  A bad Hello message 
               is one that contains inferior information that is received 
               on a port on which this bridge is Designated." 
        ::= { ebrSpan 5 } 
 
    ebrBadHelloResetTimer OBJECT-TYPE 
        SYNTAX  INTEGER 
        ACCESS  read-write 
        STATUS  mandatory 
        DESCRIPTION 
               "The number of Hello intervals without bad Hellos that 
               the bridge will wait before it resets its bad Hello 
               count to zero." 
        ::= { ebrSpan 6 } 
 
    ebrNoFrameInterval OBJECT-TYPE 
        SYNTAX  INTEGER 
 
 
        ACCESS  read-write 
        STATUS  mandatory 
        DESCRIPTION 
               "The The number of seconds of inactivity on a line that 
               will cause the bridge to run a test on that line.  The 
               bridge considers a line to be inactive if it does not 
               receive any frames on that line." 
        ::= { ebrSpan 7 } 
 
    ebrLB100PollTime OBJECT-TYPE 
        SYNTAX  INTEGER 
        ACCESS  read-write 
        STATUS  mandatory 
        DESCRIPTION 
               "The number of seconds that a Root bridge in LAN Bridge 100 
               mode waits between polling the LAN Bridge 100 that is 
               keeping it in this mode.  This polling is done to determine 
               whether the LB100 is still present on the extended LAN." 
        ::= { ebrSpan 8 } 
 
    ebrLB100ResponseTimeout OBJECT-TYPE 
        SYNTAX  INTEGER 
        ACCESS  read-write 
        STATUS  mandatory 
        DESCRIPTION 
               "The number of seconds that a Root in LAN Bridge 100 
               Spanning Tree mode will wait for a response from the 
               LAN Bridge 100 which is keeping it in this mode, before 
               which it will assume that the LB100 is no longer on 
               the extended LAN." 
        ::= { ebrSpan 9 } 
 
    ebrLB100SpanningTreeCompat OBJECT-TYPE 
        SYNTAX  INTEGER { 
                           autoSelect(1), 
                           ieee802(2) 
                        } 
        ACCESS  read-write 
        STATUS  mandatory 
        DESCRIPTION 
               "A switch that controls the Spanning Tree mode used by 
               the bridge.  If in Auto-Select mode, the bridge will 
               go into 802 Spanning Tree mode by default, but will switch 
               to LB100 mode as soon as a LB100 is detected.  In 802 
               Spanning Tree mode, the bridge will stay in 802 mode." 
        ::= { ebrSpan 10 } 
 
 
    -- ebrIfTable - the extended bridge port table 
    -- this group consists of generic port objects for the bridge 
 
    ebrIfTable OBJECT-TYPE 
        SYNTAX  SEQUENCE OF EbrIfEntry 
        ACCESS  not-accessible 
        STATUS  mandatory 
        DESCRIPTION 
               "A list of interface entries.  The number of entries is 
               given by ifNumber, defined in MIB-II." 
        ::= { ebrInterfaces 1 } 
 
    ebrIfEntry OBJECT-TYPE 
        SYNTAX  EbrIfEntry 
        ACCESS  not-accessible 
        STATUS  mandatory 
        DESCRIPTION 
               "A collection of objects containing information for a 
               given interface." 
        INDEX  { ebrIfIndex } 
        ::= { ebrIfTable 1 } 
 
    EbrIfEntry ::= 
        SEQUENCE { 
            ebrIfIndex 
                INTEGER, 
            ebrIfLinkBrokenReason 
                INTEGER, 
            ebrIfPortRestarts 
                Counter, 
            ebrIfUnknownDAReceived 
                Counter, 
            ebrIfFramesAddrFiltered 
                Counter, 
            ebrIfMultiFramesFiltered 
                Counter, 
            ebrIfFramesProtocolFiltered 
                Counter, 
            ebrIfDeviceFramesSent 
                Counter, 
            ebrIfDeviceFramesReceived 
                Counter, 
            ebrIfDeviceBytesSent 
                Counter, 
            ebrIfDeviceBytesReceived 
 
 
                Counter, 
            ebrIfDeviceFramesLost 
                Counter, 
            ebrIfMultiBytesSent 
                Counter, 
            ebrIfMultiBytesReceived 
                Counter, 
            ebrIfMultiDeviceFramesSent 
                Counter, 
            ebrIfMultiDeviceFramesReceived 
                Counter, 
            ebrIfMultiDeviceBytesSent 
                Counter, 
            ebrIfMultiDeviceBytesReceived 
                Counter, 
            ebrIfBadBytesReceived 
                Counter, 
            ebrIfBadHelloLimitExceeded 
                Counter 
             } 
 
    ebrIfIndex OBJECT-TYPE 
        SYNTAX  INTEGER 
        ACCESS  read-only 
        STATUS  mandatory 
        DESCRIPTION 
               "Identifies the Interface.  The value of this object is 
               the same as the ifIndex, defined in MIB-II, for this 
               interface." 
        ::= { ebrIfEntry 1 } 
 
    ebrIfLinkBrokenReason OBJECT-TYPE 
        SYNTAX  INTEGER { 
                           noFault(1), 
                           possibleInternalFault(2), 
                           possibleExternalFault(3) 
                        } 
        ACCESS  read-only 
        STATUS  mandatory 
        DESCRIPTION 
               "The reason why the link was last broken.  A possible 
               internal fault(1) indicates a problem with the bridge 
               line itself, a possible external fault(2), indicates 
               a problem with the transmission medium to which the 
               line is attached." 
 
 
        ::= { ebrIfEntry 2 } 
 
    ebrIfPortRestarts OBJECT-TYPE 
        SYNTAX  Counter 
        ACCESS  read-only 
        STATUS  mandatory 
        DESCRIPTION 
               "The number of times the bridge restarted the line." 
        ::= { ebrIfEntry 3 } 
 
    ebrIfUnknownDAReceived OBJECT-TYPE 
        SYNTAX  Counter 
        ACCESS  read-only 
        STATUS  mandatory 
        DESCRIPTION 
               "The number of frames received on this line for which the 
               bridge had no address entry in its forwarding database." 
        ::= { ebrIfEntry 4 } 
 
    ebrIfFramesAddrFiltered OBJECT-TYPE 
        SYNTAX  Counter 
        ACCESS  read-only 
        STATUS  mandatory 
        DESCRIPTION 
               "The number of frames filtered by the bridge on this 
               port because of address entries in the forwarding database." 
        ::= { ebrIfEntry 5 } 
 
    ebrIfMultiFramesFiltered OBJECT-TYPE 
        SYNTAX  Counter 
        ACCESS  read-only 
        STATUS  mandatory 
        DESCRIPTION 
               "The number of frames with multicast destination addresses 
               that were received on the line on the line and filtered 
               by the bridge." 
        ::= { ebrIfEntry 6 } 
 
    ebrIfFramesProtocolFiltered OBJECT-TYPE 
        SYNTAX  Counter 
        ACCESS  read-only 
        STATUS  mandatory 
        DESCRIPTION 
               "The number of frames received on this line that the 
               bridge discarded because of entries set by management 
 
 
               in the protocol database." 
        ::= { ebrIfEntry 7 } 
 
    ebrIfDeviceFramesSent OBJECT-TYPE 
        SYNTAX  Counter 
        ACCESS  read-only 
        STATUS  mandatory 
        DESCRIPTION 
               "The number of frames originating from the bridge itself 
               that were transmitted on this line." 
        ::= { ebrIfEntry 8 } 
 
    ebrIfDeviceFramesReceived OBJECT-TYPE 
        SYNTAX  Counter 
        ACCESS  read-only 
        STATUS  mandatory 
        DESCRIPTION 
               "The number of frames addressed to the bridge itself 
               that were received on this line." 
        ::= { ebrIfEntry 9 } 
 
    ebrIfDeviceBytesSent OBJECT-TYPE 
        SYNTAX  Counter 
        ACCESS  read-only 
        STATUS  mandatory 
        DESCRIPTION 
               "The number of bytes in the frames originating from the 
               bridge that were transmitted on this line." 
        ::= { ebrIfEntry 10 } 
 
    ebrIfDeviceBytesReceived OBJECT-TYPE 
        SYNTAX  Counter 
        ACCESS  read-only 
        STATUS  mandatory 
        DESCRIPTION 
               "The number of bytes in the frames addressed to the bridge 
               itself that were received on this line." 
        ::= { ebrIfEntry 11 } 
 
    ebrIfDeviceFramesLost OBJECT-TYPE 
        SYNTAX  Counter 
        ACCESS  read-only 
        STATUS  mandatory 
        DESCRIPTION 
               "The number of frames received on the line addressed 
 
 
               to the bridge itself discarded by the bridge because it 
               did not have internal buffers to store them." 
        ::= { ebrIfEntry 12 } 
 
    ebrIfMultiBytesSent OBJECT-TYPE 
        SYNTAX  Counter 
        ACCESS  read-only 
        STATUS  mandatory 
        DESCRIPTION 
               "The number of bytes in Multicast Frames sent, as reported 
               in ifOutNUcastPkts, defined in MIB-II." 
        ::= { ebrIfEntry 13 } 
 
    ebrIfMultiBytesReceived OBJECT-TYPE 
        SYNTAX  Counter 
        ACCESS  read-only 
        STATUS  mandatory 
        DESCRIPTION 
               "The number of bytes in Multicast Frames received, as 
               reported in ifInNUcastPkts, defined in MIB-II." 
        ::= { ebrIfEntry 14 } 
 
    ebrIfMultiDeviceFramesSent OBJECT-TYPE 
        SYNTAX  Counter 
        ACCESS  read-only 
        STATUS  mandatory 
        DESCRIPTION 
               "The number of frames with multicast destination addresses 
               transmitted by the bridge itself on the line." 
        ::= { ebrIfEntry 15 } 
 
    ebrIfMultiDeviceFramesReceived OBJECT-TYPE 
        SYNTAX  Counter 
        ACCESS  read-only 
        STATUS  mandatory 
        DESCRIPTION 
               "The number of frames with multicast destination addresses 
               received by the bridge itslef on the line." 
        ::= { ebrIfEntry 16 } 
 
    ebrIfMultiDeviceBytesSent OBJECT-TYPE 
        SYNTAX  Counter 
        ACCESS  read-only 
        STATUS  mandatory 
        DESCRIPTION 
 
 
               "The number of bytes in ebrIfMultiDeviceFramesSent." 
        ::= { ebrIfEntry 17 } 
 
    ebrIfMultiDeviceBytesReceived OBJECT-TYPE 
        SYNTAX  Counter 
        ACCESS  read-only 
        STATUS  mandatory 
        DESCRIPTION 
               "The number of bytes in ebrIfMultiDeviceFramesReceived." 
        ::= { ebrIfEntry 18 } 
 
    ebrIfBadBytesReceived OBJECT-TYPE 
        SYNTAX  Counter 
        ACCESS  read-only 
        STATUS  mandatory 
        DESCRIPTION 
               "The number of bytes in frames received that had a bad 
               frame check sequence." 
        ::= { ebrIfEntry 19 } 
 
    ebrIfBadHelloLimitExceeded OBJECT-TYPE 
        SYNTAX  Counter 
        ACCESS  read-only 
        STATUS  mandatory 
        DESCRIPTION 
               "The number of times that the Bad Hellos on the line 
               exceeded the Bad Hello limit." 
        ::= { ebrIfEntry 20 } 
 
    -- ebrIfEtherTable - the extended bridge Ethernet port table 
    -- this optional group consists of Ethernet port objects for the bridge 
 
    ebrIfEtherTable OBJECT-TYPE 
        SYNTAX  SEQUENCE OF EbrIfEtherEntry 
        ACCESS  not-accessible 
        STATUS  mandatory 
        DESCRIPTION 
               "A list of interface entries for an Ethernet port." 
        ::= { ebrInterfaces 2 } 
 
    ebrIfEtherEntry OBJECT-TYPE 
        SYNTAX  EbrIfEtherEntry 
        ACCESS  not-accessible 
        STATUS  mandatory 
 
 
        DESCRIPTION 
               "A collection of objects containing information for a 
               given interface." 
        INDEX  { ebrIfIndex } 
        ::= { ebrIfEtherTable 1 } 
 
    EbrIfEtherEntry ::= 
        SEQUENCE { 
            ebrIfEthIndex 
                INTEGER, 
            ebrIfEthPhysicalMediumType 
                INTEGER, 
            ebrIfEthCollisionPresenceTestSwitch 
                INTEGER, 
            ebrIfEthCollisionTestFailed 
                Counter, 
            ebrIfEthFramingError 
                Counter, 
            ebrIfEthLengthError  
                Counter, 
            ebrIfEthTransmitMultipleCollisions 
                Counter, 
            ebrIfEthCarrierLoss  
                Counter, 
            ebrIfEthCollisionLimitExceeded 
                Counter 
                 } 
 
    ebrIfEthIndex OBJECT-TYPE 
        SYNTAX  INTEGER 
        ACCESS  read-only 
        STATUS  mandatory 
        DESCRIPTION 
               "Identifies the Interface.  The value of this object is 
               the same as the ifIndex, defined in MIB-II, for this 
               interface." 
        ::= { ebrIfEtherEntry 1 } 
 
    ebrIfEthPhysicalMediumType OBJECT-TYPE 
        SYNTAX  INTEGER { 
                           stdAUIInterface(1), 
                           thinwireInterface(2), 
                           ieeeFiberInterRepeaterLink(6), 
                           fiberOpticLink850nmNoIdle(7), 
                           fiberOpticLink850nmDualIdle(8), 
 
 
                           dConnAuiIf(9), 
                           thinwireInterfaceNoLoop(10), 
                           twistedPairInterface(11), 
                           fullDuplexFiberOptic1300nm(24) 
                        } 
        ACCESS  read-only 
        STATUS  mandatory 
        DESCRIPTION 
               "The type of physical medium to which this line is 
               attached." 
        ::= { ebrIfEtherEntry 2 } 
 
    ebrIfEthCollisionPresenceTestSwitch OBJECT-TYPE 
        SYNTAX  INTEGER { 
                           true(1), 
                           false(2) 
                        } 
        ACCESS  read-write 
        STATUS  mandatory 
        DESCRIPTION 
               "A switch that informs the bridge whether the transceiver 
               on this line is using the Collision Presence Test (CPT), 
               commonly known as heartbeat.  It must be enabled if 
               the line's transceiver has CPT." 
        ::= { ebrIfEtherEntry 3 } 
 
    ebrIfEthCollisionTestFailed OBJECT-TYPE 
        SYNTAX  Counter 
        ACCESS  read-only 
        STATUS  mandatory 
        DESCRIPTION 
               "The number of times that a Collision Presence Test (CPT) 
               signal was not detected within 4 microseconds after a 
               transmission on the line.  This counter is valid only 
               if ebrIfEthCollisionPresenceTestSwitch is set to true 
               for this line." 
        ::= { ebrIfEtherEntry 4 } 
 
    ebrIfEthFramingError OBJECT-TYPE 
        SYNTAX  Counter 
        ACCESS  read-only 
        STATUS  mandatory 
        DESCRIPTION 
               "The number of times that a frame received on the line 
               contained both a noninteger multiple of 8 bits and 
 
 
               a CRC error." 
        ::= { ebrIfEtherEntry 5 } 
 
    ebrIfEthLengthError OBJECT-TYPE 
        SYNTAX  Counter 
        ACCESS  read-only 
        STATUS  mandatory 
        DESCRIPTION 
               "The number of 802.3 frames received that contained a 
               Length field inconsistent with the actual number of 
               data bytes in the packet." 
        ::= { ebrIfEtherEntry 6 } 
 
    ebrIfEthTransmitMultipleCollisions OBJECT-TYPE 
        SYNTAX  Counter 
        ACCESS  read-only 
        STATUS  mandatory 
        DESCRIPTION 
               "The number of times that the bridge had to retry 
               transmission of a frame on the line.  This was 
               because of collisions during transmission due to 
               congestion on the physical medium." 
        ::= { ebrIfEtherEntry 7 } 
 
    ebrIfEthCarrierLoss OBJECT-TYPE 
        SYNTAX  Counter 
        ACCESS  read-only 
        STATUS  mandatory 
        DESCRIPTION 
               "The number of times that the bridge detected a loss of 
               the carrier signal while transmitting a frame on the 
               line." 
        ::= { ebrIfEtherEntry 8 } 
 
    ebrIfEthCollisionLimitExceeded OBJECT-TYPE 
        SYNTAX  Counter 
        ACCESS  read-only 
        STATUS  mandatory 
        DESCRIPTION 
               "The number of times that the bridge failed to transmit 
               a frame on this line after 16 attempts, the collision 
               limit." 
        ::= { ebrIfEtherEntry 9 } 
 
    -- ebrIfFddiTable - the extended bridge FDDI port table 
 
 
    -- this group consists of FDDI port objects for the bridge 
 
    ebrIfFddiTable OBJECT-TYPE 
        SYNTAX  SEQUENCE OF EbrIfFddiEntry 
        ACCESS  not-accessible 
        STATUS  mandatory 
        DESCRIPTION 
               "A list of interface entries for an FDDI port." 
        ::= { ebrInterfaces 3 } 
 
    ebrIfFddiEntry OBJECT-TYPE 
        SYNTAX  EbrIfFddiEntry 
        ACCESS  not-accessible 
        STATUS  mandatory 
        DESCRIPTION 
               "A collection of objects containing information for a 
               given interface." 
        INDEX  { ebrIfIndex } 
        ::= { ebrIfFddiTable 1 } 
 
    EbrIfFddiEntry ::= 
        SEQUENCE { 
            ebrIfFddiIndex 
                INTEGER, 
            ebrIfFddiUnprocessedErrorPackets 
                Counter, 
            ebrIfFddiIpDatagramsFragmented 
                Counter, 
            ebrIfFddiIpDontFragment 
                Counter, 
            ebrIfFddiIpIllegalHeaderLength 
                Counter, 
            ebrIfFddiIpIllegalSize 
                Counter 
                  } 
 
    ebrIfFddiIndex OBJECT-TYPE 
        SYNTAX  INTEGER 
        ACCESS  read-only 
        STATUS  mandatory 
        DESCRIPTION 
               "Identifies the Interface.  The value of this object is 
               the same as the ifIndex, defined in MIB-II, for this 
               interface." 
        ::= { ebrIfFddiEntry 1 } 
 
 
    ebrIfFddiUnprocessedErrorPackets OBJECT-TYPE 
        SYNTAX  Counter 
        ACCESS  read-only 
        STATUS  mandatory 
        DESCRIPTION 
               "The number of times that an error frame was received 
               on thisline but the bridge did not have time to 
               decipher it." 
        ::= { ebrIfFddiEntry 2 } 
 
    ebrIfFddiIpDatagramsFragmented OBJECT-TYPE 
        SYNTAX  Counter 
        ACCESS  read-only 
        STATUS  mandatory 
        DESCRIPTION 
               "The number or large IP Datagrams that were fragmented 
               into smaller frames because they did not fit into 
               legal size packets on the smaller datalink after 
               translation." 
        ::= { ebrIfFddiEntry 3 } 
 
    ebrIfFddiIpDontFragment OBJECT-TYPE 
        SYNTAX  Counter 
        ACCESS  read-only 
        STATUS  mandatory 
        DESCRIPTION 
               "The number of large IP datagrams that could not be 
               fragmented because the DONT-FRAGMENT bit was set in 
               the IP header." 
        ::= { ebrIfFddiEntry 4 } 
 
    ebrIfFddiIpIllegalHeaderLength OBJECT-TYPE 
        SYNTAX  Counter 
        ACCESS  read-only 
        STATUS  mandatory 
        DESCRIPTION 
               "The number of large IP datagrams that were discarded 
               instead of being fragmented because the IP header was 
               of illegal length." 
        ::= { ebrIfFddiEntry 5 } 
 
    ebrIfFddiIpIllegalSize OBJECT-TYPE 
        SYNTAX  Counter 
        ACCESS  read-only 
 
 
        STATUS  mandatory 
        DESCRIPTION 
               "The number of large IP datagrams that were discarded 
               instead of being fragmented because the IP header 
               indicated a length greater than the number of actual 
               bytes in the received datagram." 
        ::= { ebrIfFddiEntry 6 } 
 
    -- ebrIfSpanTable - the extended bridge Spanning Tree port table 
    -- this group consists of port Spanning Tree objects for the bridge 
 
    ebrIfSpanTable OBJECT-TYPE 
        SYNTAX  SEQUENCE OF EbrIfSpanEntry 
        ACCESS  not-accessible 
        STATUS  mandatory 
        DESCRIPTION 
               "A list of interface entries." 
        ::= { ebrInterfaces 4 } 
 
    ebrIfSpanEntry OBJECT-TYPE 
        SYNTAX  EbrIfSpanEntry 
        ACCESS  not-accessible 
        STATUS  mandatory 
        DESCRIPTION 
               "A collection of objects containing information for a 
               given interface." 
        INDEX  { ebrIfIndex } 
        ::= { ebrIfSpanTable 1 } 
 
    EbrIfSpanEntry ::= 
        SEQUENCE { 
            ebrIfSpIndex 
                INTEGER, 
            ebrIfSpDesigRootAge 
                INTEGER, 
            ebrIfSpForwardDelayTimer 
                INTEGER, 
            ebrIfSpBadHelloCount 
                Counter, 
            ebrIfSpPossibleLoopFlag 
                INTEGER, 
            ebrIfSpTopologyChangeAckFlag 
                INTEGER 
                 } 
 
 
    ebrIfSpIndex OBJECT-TYPE 
        SYNTAX  INTEGER 
        ACCESS  read-only 
        STATUS  mandatory 
        DESCRIPTION 
               "Identifies the Interface.  The value of this object is 
               the same as the ifIndex, defined in MIB-II, for this 
               interface." 
        ::= { ebrIfSpanEntry 1 } 
 
    ebrIfSpDesigRootAge OBJECT-TYPE 
        SYNTAX  INTEGER 
        ACCESS  read-only 
        STATUS  mandatory 
        DESCRIPTION 
               "The age, in hundreths of seconds, of the last Hello 
               message received from the designated bridge on the line." 
        ::= { ebrIfSpanEntry 2 } 
 
    ebrIfSpForwardDelayTimer OBJECT-TYPE 
        SYNTAX  INTEGER 
        ACCESS  read-only 
        STATUS  mandatory 
        DESCRIPTION 
               "The time remaining, in hundreths of seconds, before the 
               bridge will leave the Preforwarding state (listening or 
               learning), and enter the Forwarding State.  If not in 
               preforwarding, this value will be reported as 0." 
        ::= { ebrIfSpanEntry 3 } 
 
    ebrIfSpBadHelloCount OBJECT-TYPE 
        SYNTAX  Counter 
        ACCESS  read-only 
        STATUS  mandatory 
        DESCRIPTION 
               "The number of Hello intervals during which at least one 
               Bad Hello was received." 
        ::= { ebrIfSpanEntry 4 } 
 
    ebrIfSpPossibleLoopFlag OBJECT-TYPE 
        SYNTAX  INTEGER { 
                           true(1), 
                           false(2) 
                        } 
        ACCESS  read-only 
 
 
        STATUS  mandatory 
        DESCRIPTION 
               "A flag that indicates whether the bridge detected a loop 
               condition on this line." 
        ::= { ebrIfSpanEntry 5 } 
 
    ebrIfSpTopologyChangeAckFlag OBJECT-TYPE 
        SYNTAX  INTEGER { 
                           true(1), 
                           false(2) 
                        } 
        ACCESS  read-only 
        STATUS  mandatory 
        DESCRIPTION 
               "A flag that indicates whether a topology change 
               notification received on a link that we are designated 
               on needs to be acknowledged." 
        ::= { ebrIfSpanEntry 6 } 
 
    -- Static Address Database for 2-port Bridges 
 
    ebrTwoPortStaticTable OBJECT-TYPE 
        SYNTAX  SEQUENCE OF EbrTwoPortStaticEntry 
        ACCESS  not-accessible 
        STATUS  mandatory 
        DESCRIPTION 
                "A table that contains static destination and source 
                 address filtering information about unicast and 
                 multicast addresses for 2-port bridges." 
        ::= { ebrTwoPortStatic 1 } 
 
    ebrTwoPortStaticEntry OBJECT-TYPE 
        SYNTAX  EbrTwoPortStaticEntry 
        ACCESS  not-accessible 
        STATUS  mandatory 
        DESCRIPTION 
                "Information about a specific MAC address 
                for which the bridge has some static forwarding and/or 
                filtering information." 
        INDEX   { ebrTwoPortAddress } 
        ::= { ebrTwoPortStaticTable 1 } 
 
    EbrTwoPortStaticEntry ::= 
        SEQUENCE { 
 
 
            ebrTwoPortAddress 
                OCTET STRING, 
            ebrTwoPortPortNum 
                INTEGER, 
            ebrTwoPortStatus 
                INTEGER 
        } 
 
    ebrTwoPortAddress OBJECT-TYPE 
        SYNTAX  OCTET STRING (SIZE (6)) 
        ACCESS  read-write 
        STATUS  mandatory 
        DESCRIPTION 
                "The destination/source MAC Address in a frame to 
                which this entry's filtering information applies." 
        ::= { ebrTwoPortStaticEntry 1 } 
 
    ebrTwoPortPortNum OBJECT-TYPE 
        SYNTAX  INTEGER 
        ACCESS  read-write 
        STATUS  mandatory 
        DESCRIPTION 
                "The Port Number to which this address will be 
                locked-down, if the status is lockDown.  Otherwise, 
                this field has a value of 0." 
        ::= { ebrTwoPortStaticEntry 2 } 
 
    ebrTwoPortStatus OBJECT-TYPE 
        SYNTAX  INTEGER { 
                    lockDown(1), 
                    hello(2), 
                    invalid(3), 
                    filter(4), 
                    forward(5), 
                    rateLimit(6) 
                } 
        ACCESS  read-write 
        STATUS  mandatory 
        DESCRIPTION 
                "The status of this entry.  The meanings of the 
                values are: 
 
                  lockDown(1) : This address is 'locked-down' to the 
                      port specified by the ebrTwoPortPortNum field. 
                      This address will be allowed to source frames 
 
 
                      only from the specified port, and frames destined 
                      to this address will be sent out only on the 
                      specified port. 
 
                  hello(2) : This is the address used by the bridge in 
                      the destination field of Spanning Tree Hellos. 
                      It is not a writeable value. 
 
                  invalid(3) : Writing this value to the object removes 
                      the corresponding entry. 
 
                  filter(4) : Frames with this address in the source or 
                      destination field will be filtered by the bridge. 
 
                  forward(5) : Frames with this address in the 
                      destination field will be forwarded by the bridge. 
 
                  rateLimit(6) : Frames with this address in the 
                      destination field will be rate-limited by the 
                      bridge, if it supports rate limiting.  Applicable 
                      only to multicast addresses.  For more detail, please 
                      see the ebrRateLimiting group." 
        ::= { ebrTwoPortStaticEntry 3 } 
 
    --  Static Database for multi-port bridges 
 
    ebrMultiPortStaticTable OBJECT-TYPE 
        SYNTAX  SEQUENCE OF EbrMultiPortStaticEntry 
        ACCESS  not-accessible 
        STATUS  mandatory 
        DESCRIPTION 
                "A table that contains static destination and source 
                 address filtering information about unicast and 
                 multicast addresses for multi-port bridges." 
        ::= { ebrMultiPortStatic 1 } 
 
    ebrMultiPortStaticEntry OBJECT-TYPE 
        SYNTAX  EbrMultiPortStaticEntry 
        ACCESS  not-accessible 
        STATUS  mandatory 
        DESCRIPTION 
                "Information about a specific MAC address 
                for which the bridge has some static forwarding and/or 
 
 
                filtering information." 
        INDEX   { ebrMultiPortAddress, ebrMultiPortReceivePort } 
        ::= { ebrMultiPortStaticTable 1 } 
 
    EbrMultiPortStaticEntry ::= 
        SEQUENCE { 
            ebrMultiPortAddress 
                OCTET STRING, 
            ebrMultiPortReceivePort 
                INTEGER, 
            ebrMultiPortAllowedToGoTo 
                OCTET STRING, 
            ebrMultiPortPortNum 
                INTEGER, 
            ebrMultiPortStatus 
                INTEGER 
        } 
 
    ebrMultiPortAddress OBJECT-TYPE 
        SYNTAX  OCTET STRING (SIZE (6)) 
        ACCESS  read-write 
        STATUS  mandatory 
        DESCRIPTION 
                "The destination/source MAC Address in a frame to 
                 which this entry's filtering information applies." 
        ::= { ebrMultiPortStaticEntry 1 } 
 
    ebrMultiPortReceivePort OBJECT-TYPE 
        SYNTAX  INTEGER 
        ACCESS  read-write 
        STATUS  mandatory 
        DESCRIPTION 
                "The port from which a frame must be received to use 
                the corresponding ebrMultiPortAllowedToGoTo field.  A value 
                of zero indicates that this entry applies on all ports of 
                the bridge." 
        ::= { ebrMultiPortStaticEntry 2 } 
 
    ebrMultiPortAllowedToGoTo OBJECT-TYPE 
        SYNTAX  OCTET STRING 
        ACCESS  read-write 
        STATUS  mandatory 
        DESCRIPTION 
                "The set of ports to which frames received from 
                a specific port and sourced from or destined to 
 
 
                the address specified by ebrMultiPortAddress are 
                allowed to be forwarded.  Each octet within the 
                value of this object specifies a set of eight ports, 
                with the first octet specifying ports 1 through 8, 
                the second octet specifying port 9 through 16 etc. 
                Within each octet, the most significant bit represents 
                the lowest numbered port, and the least significant 
                bit represents the highest numbered port.  If a 
                bit has a value of '1', then the corresponding port 
                is included in the set of ports; the port is not 
                included if its bit has a value of '0'." 
        ::= { ebrMultiPortStaticEntry 3 } 
 
    ebrMultiPortPortNum OBJECT-TYPE 
        SYNTAX  INTEGER 
        ACCESS  read-write 
        STATUS  mandatory 
        DESCRIPTION 
                "The Port Number to which this address will be 
                locked-down, if the status is lockDown.  Otherwise, 
                this field has a value of zero." 
        ::= { ebrMultiPortStaticEntry 4 } 
 
    ebrMultiPortStatus OBJECT-TYPE 
        SYNTAX  INTEGER { 
                    portMask(1), 
                    lockDown(2), 
                    maskAndLock(3), 
                    hello(4), 
                    filter(5), 
                    invalid(6), 
                    rateLimit(7), 
                    rateLimitAndPortMask(8) 
                } 
        ACCESS  read-write 
        STATUS  mandatory 
        DESCRIPTION 
                "The status of this entry.  The meanings of the 
                values are: 
 
                  portMask(1) : The static filtering for this address 
                      is specified by the MultiPortAllowedToGoTo field. 
 
                  lockDown(2) : The static filtering for this address 
                      is specified as 'locked-down' to the port specified 
 
 
                      by the ebrMultiPortPortNum field.  This address will 
                      be allowed to source frames only from the specified 
                      port, and frames destined to this address will be 
                      sent out only on the specified port.   
 
                  maskAndLock(3) : The static filtering for this 
                      address is specified by both the 
                      ebrMultiPortAllowedToGoTo as well as 'locked-down' 
                      as explained above for 'lockDown(2)'. 
 
                  hello(4) : This is the address used by the bridge in 
                      the destination field of Spanning Tree Hellos. 
                      It is not a writeable value. 
 
                  filter(5) : This address will be filtered on all ports. 
 
                  invalid(6) : Writing this value to the object removes 
                      the corresponding entry. 
 
                  rateLimit(7) : Frames with this address in the 
                      destination field will be rate-limited by the 
                      bridge, if it supports rate limiting.  Applicable 
                      only to multicast addresses.  For more detail, please 
                      see the ebrRateLimiting group. 
 
                  rateLimitAndPortMask(8) : Frames received with this 
                      address will be subjected to both rate limiting 
                      and port mask filtering." 
        ::= { ebrMultiPortStaticEntry 5 } 
 
    --  Protocol Database for two-port bridges 
 
    ebrTwoProtoEnetFilterOther OBJECT-TYPE 
        SYNTAX  INTEGER { 
                           forward(1), 
                           filter(2) 
                        } 
        ACCESS  read-write 
        STATUS  mandatory 
        DESCRIPTION 
               "Action taken by the bridge on Ethernet protocol types  
	       other than those specified in the ebrTwoEnetProtoTable. " 
        ::= { ebrTwoProtoFilt 1 } 
 
 
   ebrTwoProtoSapFilterOther OBJECT-TYPE 
        SYNTAX  INTEGER { 
                           forward(1), 
                           filter(2) 
                        } 
        ACCESS  read-write 
        STATUS  mandatory 
        DESCRIPTION 
               "Action taken by the bridge on 802.2 DSAPs other than  
               those specified in the ebrTwoSapProtoTable. " 
        ::= { ebrTwoProtoFilt 2 } 
 
   ebrTwoProtoSnapFilterOther OBJECT-TYPE 
        SYNTAX  INTEGER { 
                           forward(1), 
                           filter(2) 
                        } 
        ACCESS  read-write 
        STATUS  mandatory 
        DESCRIPTION 
               "Action taken by the bridge on the 5-byte SNAP PIDs other  
	       than those specified in the ebrTwoSnapProtoTable. " 
        ::= { ebrTwoProtoFilt 3 } 
 
    ebrTwoEnetProtoTable OBJECT-TYPE 
        SYNTAX  SEQUENCE OF EbrTwoEnetProtoEntry 
        ACCESS  not-accessible 
        STATUS  mandatory 
        DESCRIPTION 
                "A table that contains filtering information about 
                Ethernet protocol types for 2-port bridges." 
        ::= { ebrTwoProtoFilt 4 } 
 
    ebrTwoEnetProtoEntry OBJECT-TYPE 
        SYNTAX  EbrTwoEnetProtoEntry 
        ACCESS  not-accessible 
        STATUS  mandatory 
        DESCRIPTION 
                "A table that contains filtering information about 
                Ethernet protocol types for 2-port bridges." 
        INDEX   { ebrTwoEnetProtoType } 
        ::= { ebrTwoEnetProtoTable 1 } 
 
    EbrTwoEnetProtoEntry ::= 
        SEQUENCE { 
 
 
            ebrTwoEnetProtoType 
                OCTET STRING, 
            ebrTwoEnetProtoStatus 
                INTEGER 
                 } 
 
    ebrTwoEnetProtoType OBJECT-TYPE 
        SYNTAX  OCTET STRING (SIZE (2)) 
        ACCESS  read-write 
        STATUS  mandatory 
        DESCRIPTION 
                "The protocol type in a frame to which this entry's 
                filtering information applies." 
        ::= { ebrTwoEnetProtoEntry 1 } 
 
    ebrTwoEnetProtoStatus OBJECT-TYPE 
        SYNTAX  INTEGER { 
                           forward(1), 
                           filter(2), 
                           invalid(3), 
                           rateLimit(4) 
                        } 
        ACCESS  read-write 
        STATUS  mandatory 
        DESCRIPTION 
                "Action taken by bridge when it sees this ethernet 
                protocol type in a received frame.  The meanings of 
                the values are: 
 
                  forward(1) : Frames received with this protocol type 
                     are allowed to be forwarded. 
 
                  filter(2) : Frames received with this protocol type 
                     should be filtered. 
 
                  invalid(3) : Writing this value to the object removes 
                      the corresponding entry. 
 
                  rateLimit(4) : Frames received with this protocol type 
                      will be rate-limited by the bridge, if it supports 
                      rate limiting.  For more detail, please 
                      see the ebrRateLimiting group." 
        ::= { ebrTwoEnetProtoEntry 2 } 
 
    ebrTwoSapProtoTable OBJECT-TYPE 
 
 
        SYNTAX  SEQUENCE OF EbrTwoSapProtoEntry 
        ACCESS  not-accessible 
        STATUS  mandatory 
        DESCRIPTION 
                "A table that contains filtering information about 
                802.2 SAPs in the DSAP field for 2-port bridges." 
        ::= { ebrTwoProtoFilt 5 } 
 
    ebrTwoSapProtoEntry OBJECT-TYPE 
        SYNTAX  EbrTwoSapProtoEntry 
        ACCESS  not-accessible 
        STATUS  mandatory 
        DESCRIPTION 
                "A table that contains filtering information about 
                802.2 SAPs in the DSAP field for 2-port bridges." 
        INDEX   { ebrTwoSapIndex } 
        ::= { ebrTwoSapProtoTable 1 } 
 
    EbrTwoSapProtoEntry ::= 
        SEQUENCE { 
            ebrTwoSapIndex 
                INTEGER, 
            ebrTwoSapValue 
                OCTET STRING, 
            ebrTwoSapStatus 
                INTEGER 
                 } 
 
   ebrTwoSapIndex OBJECT-TYPE 
        SYNTAX  INTEGER (1..256) 
        ACCESS  read-only 
        STATUS  mandatory 
        DESCRIPTION 
                "Index of the SAP table." 
        ::= { ebrTwoSapProtoEntry 1 } 
 
    ebrTwoSapValue OBJECT-TYPE 
        SYNTAX  OCTET STRING (SIZE (1)) 
        ACCESS  read-write 
        STATUS  mandatory 
        DESCRIPTION 
                "The 802.2 DSAP in a frame to which this entry's 
                filtering information applies." 
        ::= { ebrTwoSapProtoEntry 2 } 
 
 
    ebrTwoSapStatus OBJECT-TYPE 
        SYNTAX  INTEGER { 
                           forward(1), 
                           filter(2), 
                           invalid(3), 
                           rateLimit(4) 
                        } 
        ACCESS  read-write 
        STATUS  mandatory 
        DESCRIPTION 
                "Action taken by bridge when it sees this 802.2 SAP 
                in the DSAP field of a received frame.  The meanings of 
                the values are: 
 
                 forward(1) : Frames received with this sap 
                     are allowed to be forwarded. 
 
                 filter(2) : Frames received with this sap 
                     should be filtered. 
 
                  invalid(3) : Writing this value to the object removes 
                      the corresponding entry. 
 
                  rateLimit(4) : Frames received with this sap 
                      will be rate-limited by the bridge, if it supports 
                      rate limiting.  For more detail, please 
                      see the ebrRateLimiting group." 
        ::= { ebrTwoSapProtoEntry 3 } 
 
    ebrTwoSnapProtoTable OBJECT-TYPE 
        SYNTAX  SEQUENCE OF EbrTwoSnapProtoEntry 
        ACCESS  not-accessible 
        STATUS  mandatory 
        DESCRIPTION 
                "A table that contains filtering information about 
                5-byte SNAP PIDs for 2-port bridges." 
        ::= { ebrTwoProtoFilt 6 } 
 
    ebrTwoSnapProtoEntry OBJECT-TYPE 
        SYNTAX  EbrTwoSnapProtoEntry 
        ACCESS  not-accessible 
        STATUS  mandatory 
        DESCRIPTION 
                "A table that contains filtering information about 
                5-byte SNAP PIDs for 2-port bridges." 
 
 
        INDEX   { ebrTwoSnapIndex } 
        ::= { ebrTwoSnapProtoTable 1 } 
 
    EbrTwoSnapProtoEntry ::= 
        SEQUENCE { 
            ebrTwoSnapIndex 
                INTEGER, 
            ebrTwoSnapValue 
                OCTET STRING, 
            ebrTwoSnapStatus 
                INTEGER 
                 } 
 
      ebrTwoSnapIndex OBJECT-TYPE 
        SYNTAX  INTEGER 
        ACCESS  read-only 
        STATUS  mandatory 
        DESCRIPTION 
                "The index into the SNAP table." 
        ::= { ebrTwoSnapProtoEntry 1 } 
 
      ebrTwoSnapValue OBJECT-TYPE 
        SYNTAX  OCTET STRING (SIZE (5)) 
        ACCESS  read-write 
        STATUS  mandatory 
        DESCRIPTION 
                "The SNAP PID in an 802 frame to which this entry's 
                filtering information applies." 
        ::= { ebrTwoSnapProtoEntry 2 } 
 
    ebrTwoSnapStatus OBJECT-TYPE 
        SYNTAX  INTEGER { 
                           forward(1), 
                           filter(2), 
                           invalid(3), 
                           rateLimit(4) 
                        } 
        ACCESS  read-write 
        STATUS  mandatory 
        DESCRIPTION 
                "Action taken by bridge when it sees this SNAP PID 
                in a received 802 frame.  The meanings of 
                the values are: 
 
                  forward(1) : Frames received with this snap pid 
 
 
                     are allowed to be forwarded. 
 
                  filter(2) : Frames received with this snap pid 
                     should be filtered. 
 
                  invalid(3) : Writing this value to the object removes 
                      the corresponding entry. 
 
                  rateLimit(4) : Frames received with this snap pid 
                      will be rate-limited by the bridge, if it supports 
                      rate limiting.  For more detail, please 
                      see the ebrRateLimiting group." 
        ::= { ebrTwoSnapProtoEntry 3 } 
 
    --  Protocol Database for multi-port bridges 
 
    ebrMultiEnetProtoTable OBJECT-TYPE 
        SYNTAX  SEQUENCE OF EbrMultiEnetProtoEntry 
        ACCESS  not-accessible 
        STATUS  mandatory 
        DESCRIPTION 
                "A table that contains filtering information about 
                Ethernet protocol types for multi-port bridges." 
        ::= { ebrMultiProtoFilt 1 } 
 
    ebrMultiEnetProtoEntry OBJECT-TYPE 
        SYNTAX  EbrMultiEnetProtoEntry 
        ACCESS  not-accessible 
        STATUS  mandatory 
        DESCRIPTION 
                "A table that contains filtering information about 
                Ethernet protocol types for multi-port bridges." 
        INDEX   { ebrMultiEnetProtoType, ebrMultiEnetReceivePort } 
        ::= { ebrMultiEnetProtoTable 1 } 
 
    EbrMultiEnetProtoEntry ::= 
        SEQUENCE { 
            ebrMultiEnetProtoType 
                OCTET STRING, 
            ebrMultiEnetReceivePort 
                INTEGER, 
            ebrMultiEnetAllowedToGoTo 
                OCTET STRING, 
 
 
            ebrMultiEnetStatus 
                INTEGER 
                 } 
 
    ebrMultiEnetProtoType OBJECT-TYPE 
        SYNTAX  OCTET STRING (SIZE (2)) 
        ACCESS  read-write 
        STATUS  mandatory 
        DESCRIPTION 
                "The protocol type in a frame to which this entry's 
                filtering information applies." 
        ::= { ebrMultiEnetProtoEntry 1 } 
 
    ebrMultiEnetReceivePort OBJECT-TYPE 
        SYNTAX  INTEGER 
        ACCESS  read-write 
        STATUS  mandatory 
        DESCRIPTION 
                "The port from which a frame must be received to use 
                the corresponding ebrMultiPortEnetProtoType field.  A value 
                of zero indicates that this entry applies on all ports of 
                the bridge." 
        ::= { ebrMultiEnetProtoEntry 2 } 
 
    ebrMultiEnetAllowedToGoTo OBJECT-TYPE 
        SYNTAX  OCTET STRING 
        ACCESS  read-write 
        STATUS  mandatory 
        DESCRIPTION 
                "The set of ports to which frames received from 
                a specific port and containing the protocol 
                type specified by ebrMultiEnetProtoType are 
                allowed to be forwarded.  Each octet within the 
                value of this object specifies a set of eight ports, 
                with the first octet specifying ports 1 through 8, 
                the second octet specifying port 9 through 16 etc. 
                Within each octet, the most significant bit represents 
                the lowest numbered port, and the least significant 
                bit represents the highest numbered port.  If a 
                bit has a value of '1', then the corresponding port 
                is included in the set of ports; the port is not 
                included if its bit has a value of '0'." 
        ::= { ebrMultiEnetProtoEntry 3 } 
 
    ebrMultiEnetStatus OBJECT-TYPE 
 
 
        SYNTAX  INTEGER { 
                           portMask(1), 
                           invalid(2), 
                           filter(3), 
                           forward(4), 
                           rateLimit(5), 
                           rateLimitAndPortMask(6) 
                        } 
        ACCESS  read-write 
        STATUS  mandatory 
        DESCRIPTION 
                "Action taken by bridge when it sees this ethernet 
                protocol type in a received frame.  The meanings of 
                the values are: 
 
                  portMask(1) : The static filtering for this address 
                      is specified by the MultiEnetAllowedToGoTo field. 
 
                  invalid(2) : Writing this value to the object removes 
                      the corresponding entry. 
 
                  filter(3) : Frames received with this protocol type 
                     should be filtered. 
 
                  forward(4) : Frames received with this protocol type 
                     are allowed to be forwarded. 
 
                  rateLimit(5) : Frames received with this protocol type 
                      will be rate-limited by the bridge, if it supports 
                      rate limiting.  For more detail, please 
                      see the ebrRateLimiting group. 
 
                  rateLimitAndPortMask(6) : Frames received with this 
                      protocol type will be subjected to both rate limiting 
                      and port mask filtering." 
        ::= { ebrMultiEnetProtoEntry 4 } 
 
    ebrMultiSapProtoTable OBJECT-TYPE 
        SYNTAX  SEQUENCE OF EbrMultiSapProtoEntry 
        ACCESS  not-accessible 
        STATUS  mandatory 
        DESCRIPTION 
                "A table that contains filtering information about 
                802.2 SAPs in the DSAP field for multi-port bridges." 
        ::= { ebrMultiProtoFilt 2 } 
 
 
    ebrMultiSapProtoEntry OBJECT-TYPE 
        SYNTAX  EbrMultiSapProtoEntry 
        ACCESS  not-accessible 
        STATUS  mandatory 
        DESCRIPTION 
                "A table that contains filtering information about 
                802.2 SAPs in the DSAP field for multi-port bridges." 
        INDEX   { ebrMultiSapValue, ebrMultiSapReceivePort } 
        ::= { ebrMultiSapProtoTable 1 } 
 
    EbrMultiSapProtoEntry ::= 
        SEQUENCE { 
            ebrMultiSapValue 
                OCTET STRING, 
            ebrMultiSapReceivePort 
                INTEGER, 
            ebrMultiSapAllowedToGoTo 
                OCTET STRING, 
            ebrMultiSapStatus 
                INTEGER 
                 } 
 
    ebrMultiSapValue OBJECT-TYPE 
        SYNTAX  OCTET STRING (SIZE (1)) 
        ACCESS  read-write 
        STATUS  mandatory 
        DESCRIPTION 
                "The 802.2 DSAP in a frame to which this entry's 
                filtering information applies." 
        ::= { ebrMultiSapProtoEntry 1 } 
 
    ebrMultiSapReceivePort OBJECT-TYPE 
        SYNTAX  INTEGER 
        ACCESS  read-write 
        STATUS  mandatory 
        DESCRIPTION 
                "The port from which a frame must be received to use 
                the corresponding ebrMultiPortSapProtoType field.  A value 
                of zero indicates that this entry applies on all ports of 
                the bridge." 
        ::= { ebrMultiSapProtoEntry 2 } 
 
    ebrMultiSapAllowedToGoTo OBJECT-TYPE 
        SYNTAX  OCTET STRING 
 
 
        ACCESS  read-write 
        STATUS  mandatory 
        DESCRIPTION 
                "The set of ports to which frames received from 
                a specific port and containing the DSAP in an 802 
                frame specified by ebrMultiSapValue are 
                allowed to be forwarded.  Each octet within the 
                value of this object specifies a set of eight ports, 
                with the first octet specifying ports 1 through 8, 
                the second octet specifying port 9 through 16 etc. 
                Within each octet, the most significant bit represents 
                the lowest numbered port, and the least significant 
                bit represents the highest numbered port.  If a 
                bit has a value of '1', then the corresponding port 
                is included in the set of ports; the port is not 
                included if its bit has a value of '0'." 
        ::= { ebrMultiSapProtoEntry 3 } 
 
    ebrMultiSapStatus OBJECT-TYPE 
        SYNTAX  INTEGER { 
                           portMask(1), 
                           invalid(2), 
                           filter(3), 
                           forward(4), 
                           rateLimit(5), 
                           rateLimitAndPortMask(6) 
                        } 
        ACCESS  read-write 
        STATUS  mandatory 
        DESCRIPTION 
                "Action taken by bridge when it sees this 802.2 SAP 
                in the DSAP field of a received frame.  The meanings of 
                the values are: 
 
                  portMask(1) : The static filtering for this address 
                      is specified by the MultiSapAllowedToGoTo field. 
 
                  invalid(2) : Writing this value to the object removes 
                      the corresponding entry. 
 
                  filter(3) : Frames received with this protocol type 
                     should be filtered. 
 
                  forward(4) : Frames received with this protocol type 
                     are allowed to be forwarded. 
 
 
                  rateLimit(5) : Frames received with this protocol type 
                      will be rate-limited by the bridge, if it supports 
                      rate limiting.  For more detail, please 
                      see the ebrRateLimiting group. 
 
                  rateLimitAndPortMask(6) : Frames received with this 
                      protocol type will be subjected to both rate limiting 
                      and port mask filtering." 
        ::= { ebrMultiSapProtoEntry 4 } 
 
    ebrMultiSnapProtoTable OBJECT-TYPE 
        SYNTAX  SEQUENCE OF EbrMultiSnapProtoEntry 
        ACCESS  not-accessible 
        STATUS  mandatory 
        DESCRIPTION 
                "A table that contains filtering information about 
                5-byte SNAP PIDs for multi-port bridges." 
        ::= { ebrMultiProtoFilt 3 } 
 
    ebrMultiSnapProtoEntry OBJECT-TYPE 
        SYNTAX  EbrMultiSnapProtoEntry 
        ACCESS  not-accessible 
        STATUS  mandatory 
        DESCRIPTION 
                "A table that contains filtering information about 
                5-byte SNAP PIDs for multi-port bridges." 
        INDEX   { ebrMultiSnapValue, ebrMultiSnapReceivePort } 
        ::= { ebrMultiSnapProtoTable 1 } 
 
    EbrMultiSnapProtoEntry ::= 
        SEQUENCE { 
            ebrMultiSnapValue 
                OCTET STRING, 
            ebrMultiSnapReceivePort 
                INTEGER, 
            ebrMultiSnapAllowedToGoTo 
                OCTET STRING, 
            ebrMultiSnapStatus 
                INTEGER 
                 } 
 
      ebrMultiSnapValue OBJECT-TYPE 
        SYNTAX  OCTET STRING (SIZE (5)) 
        ACCESS  read-write 
 
 
        STATUS  mandatory 
        DESCRIPTION 
                "The SNAP PID in an 802 frame to which this entry's 
                filtering information applies." 
        ::= { ebrMultiSnapProtoEntry 1 } 
 
    ebrMultiSnapReceivePort OBJECT-TYPE 
        SYNTAX  INTEGER 
        ACCESS  read-write 
        STATUS  mandatory 
        DESCRIPTION 
                "The port from which a frame must be received to use 
                the corresponding ebrMultiPortSnapProtoType field.  A value 
                of zero indicates that this entry applies on all ports of 
                the bridge." 
        ::= { ebrMultiSnapProtoEntry 2 } 
 
    ebrMultiSnapAllowedToGoTo OBJECT-TYPE 
        SYNTAX  OCTET STRING 
        ACCESS  read-write 
        STATUS  mandatory 
        DESCRIPTION 
                "The set of ports to which frames received from 
                a specific port and containing the SNAP PID in an 
                802 frame specified by ebrMultiSnapValue are 
                allowed to be forwarded.  Each octet within the 
                value of this object specifies a set of eight ports, 
                with the first octet specifying ports 1 through 8, 
                the second octet specifying port 9 through 16 etc. 
                Within each octet, the most significant bit represents 
                the lowest numbered port, and the least significant 
                bit represents the highest numbered port.  If a 
                bit has a value of '1', then the corresponding port 
                is included in the set of ports; the port is not 
                included if its bit has a value of '0'." 
        ::= { ebrMultiSnapProtoEntry 3 } 
 
    ebrMultiSnapStatus OBJECT-TYPE 
        SYNTAX  INTEGER { 
                           portMask(1), 
                           invalid(2), 
                           filter(3), 
                           forward(4), 
                           rateLimit(5), 
                           rateLimitAndPortMask(6) 
 
 
                        } 
        ACCESS  read-write 
        STATUS  mandatory 
        DESCRIPTION 
                "Action taken by bridge when it sees this SNAP PID 
                in a received 802 frame.  The meanings of 
                the values are: 
 
                  portMask(1) : The static filtering for this address 
                      is specified by the MultiSnapAllowedToGoTo field. 
 
                  invalid(2) : Writing this value to the object removes 
                      the corresponding entry. 
 
                  filter(3) : Frames received with this protocol type 
                     should be filtered. 
 
                  forward(4) : Frames received with this protocol type 
                     are allowed to be forwarded. 
 
                  rateLimit(5) : Frames received with this protocol type 
                      will be rate-limited by the bridge, if it supports 
                      rate limiting.  For more detail, please 
                      see the ebrRateLimiting group. 
 
                  rateLimitAndPortMask(6) : Frames received with this 
                      protocol type will be subjected to both rate limiting 
                      and port mask filtering." 
        ::= { ebrMultiSnapProtoEntry 4 } 
 
    -- ebrMultiFiltSw - this optional group consists of per-port 
    -- address and protocol filtering switches for multiport bridges 
 
    ebrMultiSwTable OBJECT-TYPE 
        SYNTAX  SEQUENCE OF EbrMultiSwEntry 
        ACCESS  not-accessible 
        STATUS  mandatory 
        DESCRIPTION 
               "A list of interface entries.  The number of entries is 
               given by ifNumber, defined in MIB-II." 
        ::= { ebrMultiFiltSw 1 } 
 
    ebrMultiSwEntry OBJECT-TYPE 
 
 
        SYNTAX  EbrMultiSwEntry 
        ACCESS  not-accessible 
        STATUS  mandatory 
        DESCRIPTION 
               "A collection of objects containing information for a 
               given interface." 
        INDEX  { ebrMultiSwIndex } 
        ::= { ebrMultiSwTable 1 } 
 
    EbrMultiSwEntry ::= 
        SEQUENCE { 
            ebrMultiSwIndex 
                INTEGER, 
            ebrMultiSwManualFilter 
                INTEGER, 
            ebrMultiSwProtoEnetOther 
                INTEGER, 
            ebrMultiSwProtoSapOther 
                INTEGER, 
            ebrMultiSwProtoSnapOther 
                INTEGER 
                 } 
 
    ebrMultiSwIndex OBJECT-TYPE 
        SYNTAX  INTEGER 
        ACCESS  read-only 
        STATUS  mandatory 
        DESCRIPTION 
               "Identifies the Interface to which this entry applies." 
        ::= { ebrMultiSwEntry 1 } 
 
    ebrMultiSwManualFilter OBJECT-TYPE 
        SYNTAX  INTEGER { 
                           true(1), 
                           false(2) 
                        } 
        ACCESS  read-write 
        STATUS  mandatory 
        DESCRIPTION 
               "A switch that controls address filtering.  When true, 
               the bridge purges the learned entries from its forwarding 
               database, stops its learning process, and forwards only 
               frames with destination and source addresses that have 
               been specified via management." 
        ::= { ebrMultiSwEntry 2 } 
 
 
    ebrMultiSwProtoEnetOther OBJECT-TYPE 
        SYNTAX  INTEGER { 
                           forward(1), 
                           filter(2) 
                        } 
        ACCESS  read-write 
        STATUS  mandatory 
        DESCRIPTION 
               "Action taken by the bridge on Ethernet protocol types 
               other than those specified in the ebrMultiEnetProtoTable." 
        ::= { ebrMultiSwEntry 3 } 
 
    ebrMultiSwProtoSapOther OBJECT-TYPE 
        SYNTAX  INTEGER { 
                           forward(1), 
                           filter(2) 
                        } 
        ACCESS  read-write 
        STATUS  mandatory 
        DESCRIPTION 
               "Action taken by the bridge on 802.2 DSAPs other  
	       than those specified in the ebrMultiSapProtoTable." 
        ::= { ebrMultiSwEntry 4 } 
 
    ebrMultiSwProtoSnapOther OBJECT-TYPE 
        SYNTAX  INTEGER { 
                           forward(1), 
                           filter(2) 
                        } 
        ACCESS  read-write 
        STATUS  mandatory 
        DESCRIPTION 
               "Action taken by the bridge on the 5-byte SNAP PIDs other  
	       than those specified in the ebrMultiSnapProtoTable." 
        ::= { ebrMultiSwEntry 5 } 
 
    -- 
    -- ebrNTP  - the Non-Translated Protocol table. 
    -- 
    -- this optional group is implemented by FDDI to Ethernet bridges which 
    -- support this feature.  Selected Ethernet Protocol types are 
    -- subjected to a different algorithm than the standard translation 
    -- algorithm used by transparent FDDI to Ethernet bridges.  It is 
    -- used for protocol types that may be used in both Ethernet packets 
 
 
    -- as well as IEEE 802.3 packets with a 1042-style PID.  An example 
    -- of a protocol type that should be in this table is AARP. 
    -- 
 
    ebrNTPTable OBJECT-TYPE 
        SYNTAX  SEQUENCE OF EbrNTPEntry 
        ACCESS  not-accessible 
        STATUS  mandatory 
        DESCRIPTION 
               "A table of Ethernet protocol types which will 
               selectively be translated in such a way as to guarantee 
               that the form in which a packet was received - Ethernet PT 
               or 802.3 with 1042 format and this PT - will be retained 
               across a pair of these bridges." 
        ::= { ebrNTP 1 } 
 
    ebrNTPEntry OBJECT-TYPE 
        SYNTAX  EbrNTPEntry 
        ACCESS  not-accessible 
        STATUS  mandatory 
        DESCRIPTION 
               "A list of NTP protocol type entries." 
        INDEX   { ebrNTPtype } 
        ::= { ebrNTPTable 1 } 
 
    EbrNTPEntry ::= 
        SEQUENCE { 
            ebrNTPtype 
                OCTET STRING, 
            ebrNTPStatus 
                INTEGER 
                 } 
 
    ebrNTPtype OBJECT-TYPE 
        SYNTAX  OCTET STRING (SIZE (2)) 
        ACCESS  read-write 
        STATUS  mandatory 
        DESCRIPTION 
               "A protocol type in the NTP table." 
        ::= { ebrNTPEntry 1 } 
 
    ebrNTPStatus OBJECT-TYPE 
        SYNTAX  INTEGER { 
                           other(1), 
                           invalid(2) 
 
 
                        } 
        ACCESS  read-write 
        STATUS  mandatory 
        DESCRIPTION 
               "Writing invalid(2) to this object removes the corresponding 
               entry.  When read, this object always returns a value 
               of other(1)." 
        ::= { ebrNTPEntry 2 } 
 
    esysIPXSwitch OBJECT-TYPE 
        SYNTAX  INTEGER { 
                           true(1), 
                           false(2) 
                        } 
        ACCESS  read-write 
        STATUS  mandatory 
        DESCRIPTION 
               "A software switch that, when set to true, causes the 
               bridge to translate IPX 'raw 802.3' packets into SNAP 
               encapsulated packets on the FDDI.  Note that this works 
               only in environments where all IPX stations use only 
               this particular format.  It is recommended that the 
               Ethernet v2 format be used on IPX stations for 
               full connectivity of IPX stations across Ethernet 
               as well as FDDI bridged and routed networks." 
        ::= { ebrNTP 2 } 
 
    -- 
    -- ebrRateLimit  - the Rate Limit group 
    -- 
    -- this optional group is implemented by bridges which perform rate 
    -- limiting of multicast frames received on bridge ports.  A typical 
    -- application of this might be to limit a broadcast storm from 
    -- to the confines of the LAN connected by the bridge. 
    -- 
    -- Rate limiting may be specified by address or protocol, via the 
    -- appropriate static address or protocol database, through the use 
    -- of the 'rateLimit' status. 
    -- 
 
    ebrRateLimitSwitch OBJECT-TYPE 
        SYNTAX  INTEGER { 
                           true(1), 
                           false(2) 
                        } 
 
 
        ACCESS  read-write 
        STATUS  mandatory 
        DESCRIPTION 
               "By default, rate limiting will be disabled.  It can be 
               enabled by setting this object to 'true(1)'." 
        ::= { ebrRateLimiting 1 } 
 
    ebrRateLimit OBJECT-TYPE 
        SYNTAX  INTEGER 
        ACCESS  read-write 
        STATUS  mandatory 
        DESCRIPTION 
               "This is the maximum number of rate-limited frames per second 
               that the bridge will forward per second." 
        ::= { ebrRateLimiting 2 } 
 
    ebrRateLimitCounterTable OBJECT-TYPE 
        SYNTAX  SEQUENCE OF EbrRateLimitCounterEntry 
        ACCESS  not-accessible 
        STATUS  mandatory 
        DESCRIPTION 
               "A table of the count of frames that were dropped by 
               the bridge due to rate limiting on each port." 
        ::= { ebrRateLimiting 3 } 
 
    ebrRateLimitCounterEntry OBJECT-TYPE 
        SYNTAX  EbrRateLimitCounterEntry 
        ACCESS  not-accessible 
        STATUS  mandatory 
        DESCRIPTION 
               "A list of rate limited frame counter entries." 
        INDEX   { ebrRateLimitPort } 
        ::= { ebrRateLimitCounterTable 1 } 
 
    EbrRateLimitCounterEntry ::= 
        SEQUENCE { 
            ebrRateLimitPort 
                INTEGER, 
            ebrRateLimitAddressFrames 
                Counter, 
            ebrRateLimitProtocolFrames 
                Counter 
                 } 
 
    ebrRateLimitPort OBJECT-TYPE 
 
 
        SYNTAX  INTEGER 
        ACCESS  read-only 
        STATUS  mandatory 
        DESCRIPTION 
               "The port for which this entry contains rate limit 
               counters information." 
        ::= { ebrRateLimitCounterEntry 1 } 
 
    ebrRateLimitAddressFrames OBJECT-TYPE 
        SYNTAX  Counter 
        ACCESS  read-only 
        STATUS  mandatory 
        DESCRIPTION 
               "This is the number of frames per second that were 
               filtered due to address rate limiting." 
        ::= { ebrRateLimitCounterEntry 2 } 
 
    ebrRateLimitProtocolFrames OBJECT-TYPE 
        SYNTAX  Counter 
        ACCESS  read-only 
        STATUS  mandatory 
        DESCRIPTION 
               "This is the number of frames per second that were 
               filtered due to protocol rate limiting." 
        ::= { ebrRateLimitCounterEntry 3 } 
 
    -- 
    -- ebrSpanTurnOff  - turning off Spanning Tree 
    -- 
    -- this optional group is implemented by bridges which allow Spanning 
    -- Tree to be turned off on particular ports.  It consists of a table 
    -- of bridge ports with associated status.  On such ports, received 
    -- hello messages of both 802.1D and DEC LB100 protocols are dropped 
    -- without any processing.  In addition, no hellos are generated. 
    -- 
    -- NOTE: Turning off spanning tree is not recommended.  It can cause 
    -- the extended LAN to go down or thrash due to loops. 
    -- 
 
    ebrIfSpanTurnOffTable OBJECT-TYPE 
        SYNTAX  SEQUENCE OF EbrIfSpanTurnOffEntry 
        ACCESS  not-accessible 
        STATUS  mandatory 
 
 
        DESCRIPTION 
               "A list of port entries." 
        ::= { ebrSpanTurnOff 1 } 
 
    ebrIfSpanTurnOffEntry OBJECT-TYPE 
        SYNTAX  EbrIfSpanTurnOffEntry 
        ACCESS  not-accessible 
        STATUS  mandatory 
        DESCRIPTION 
               "A collection of objects containing information for 
               a given bridge port." 
        INDEX  { ebrIfSpanTurnOffPort } 
        ::= { ebrIfSpanTurnOffTable 1 } 
 
    EbrIfSpanTurnOffEntry ::= 
        SEQUENCE { 
            ebrIfSpanTurnOffPort 
                INTEGER, 
            ebrIfSpanTurnOffStatus 
                INTEGER 
                 } 
 
    ebrIfSpanTurnOffPort OBJECT-TYPE 
        SYNTAX  INTEGER 
        ACCESS  read-write 
        STATUS  mandatory 
        DESCRIPTION 
               "Identifies the bridge port number of an interface." 
        ::= { ebrIfSpanTurnOffEntry 1 } 
 
    ebrIfSpanTurnOffStatus OBJECT-TYPE 
        SYNTAX  INTEGER { 
                           spanningTreeOn(1), 
                           spanningTreeOff(2) 
                        } 
        ACCESS  read-write 
        STATUS  mandatory 
        DESCRIPTION 
               "Indicates whether spanning tree is turned on or off 
               on this bridge port." 
        ::= { ebrIfSpanTurnOffEntry 2 } 
 
 
    -- 
    -- eauth   - groups in the SNMP Authentication module 
    -- 
 
    eauth1            OBJECT IDENTIFIER ::= { eauth 1 } 
 
    -- 
    -- eauth1 is a group of objects supporting simple SNMP Authentication. 
    -- 
 
    -- 
    -- SNMP Trap User Community 
    -- 
 
    eauthTrapCommunity OBJECT-TYPE 
        SYNTAX  OCTET STRING (SIZE (32)) 
        ACCESS  read-write 
        STATUS  mandatory 
        DESCRIPTION 
               "The community string used in SNMP Trap PDUs." 
    ::= { eauth1 1 } 
 
    eauthTrapUserTable OBJECT-TYPE 
        SYNTAX  SEQUENCE OF EauthTrapUserEntry 
        ACCESS  not-accessible 
        STATUS  mandatory 
        DESCRIPTION 
               "A list of addresses to which traps will be sent and 
               associated information." 
    ::= { eauth1 2 } 
 
    eauthTrapUserEntry OBJECT-TYPE 
        SYNTAX  EauthTrapUserEntry 
        ACCESS  not-accessible 
        STATUS  mandatory 
        DESCRIPTION 
               "Objects containing information for a given trap address." 
        INDEX  { eauthTrapUserAddr } 
        ::= { eauthTrapUserTable 1 } 
 
    EauthTrapUserEntry ::= 
        SEQUENCE { 
            eauthTrapUserAddr 
                IpAddress, 
 
 
            eauthTrapUserStatus 
                INTEGER 
                 } 
 
    eauthTrapUserAddr OBJECT-TYPE 
        SYNTAX  IpAddress 
        ACCESS  read-write 
        STATUS  mandatory 
        DESCRIPTION 
               "An IP Address to which all SNMP Trap messages will be sent." 
    ::= { eauthTrapUserEntry 1 } 
 
    eauthTrapUserStatus OBJECT-TYPE 
        SYNTAX  INTEGER { 
                           other(1), 
                           invalid(2) 
                        } 
        ACCESS  read-write 
        STATUS  mandatory 
        DESCRIPTION 
               "Writing invalid(2) to this object removes the corresponding 
               entry.  When read, this object always returns a value 
               of other(1)." 
    ::= { eauthTrapUserEntry 2 } 
 
    -- 
    -- SNMP Read-only User Community 
    -- 
 
    eauthReadOnlyCommunity OBJECT-TYPE 
        SYNTAX  OCTET STRING (SIZE (32)) 
        ACCESS  read-write 
        STATUS  mandatory 
        DESCRIPTION 
               "The community string used to identify an SNMP community 
               with access rights of Read-only." 
    ::= { eauth1 3 } 
 
    eauthReadOnlyUserTable OBJECT-TYPE 
        SYNTAX  SEQUENCE OF EauthReadOnlyUserEntry 
        ACCESS  not-accessible 
        STATUS  mandatory 
        DESCRIPTION 
               "A list of Read-only users and associated information." 
 
 
    ::= { eauth1 4 } 
 
    eauthReadOnlyUserEntry OBJECT-TYPE 
        SYNTAX  EauthReadOnlyUserEntry 
        ACCESS  not-accessible 
        STATUS  mandatory 
        DESCRIPTION 
               "Objects containing information for a given Read-only user." 
        INDEX  { eauthReadOnlyUserAddr } 
        ::= { eauthReadOnlyUserTable 1 } 
 
    EauthReadOnlyUserEntry ::= 
        SEQUENCE { 
            eauthReadOnlyUserAddr 
                IpAddress, 
            eauthReadOnlyUserMask 
                OCTET STRING, 
            eauthReadOnlyUserStatus 
                INTEGER 
                 } 
 
    eauthReadOnlyUserAddr OBJECT-TYPE 
        SYNTAX  IpAddress 
        ACCESS  read-write 
        STATUS  mandatory 
        DESCRIPTION 
               "An IP Address, or a set of IP addresses, which has 
               Read-only SNMP access to this agent.  If this object 
               is used as a wildcard, bits corresponding to the 
               zero bits in the corresponding euthReadOnlyUserMask 
               are treated as don't-care." 
    ::= { eauthReadOnlyUserEntry 1 } 
 
    eauthReadOnlyUserMask OBJECT-TYPE 
        SYNTAX  OCTET STRING (SIZE (4)) 
        ACCESS  read-write 
        STATUS  mandatory 
        DESCRIPTION 
               "A 32-bit mask which is applied to (ANDed with) 
               the source IP address of an incoming SNMP message. 
               If the result of the mask is equal to eauthReadOnlyUserAddr, 
               the message is considered to have come from a user 
               who has Read-only access.  This allows wildcarding, 
               for example, for all NMS's on a given subnet.  For 
               fully specified IP addresses required to be in this 
 
 
               community, this mask may be set to all 1's." 
    ::= { eauthReadOnlyUserEntry 2 } 
 
    eauthReadOnlyUserStatus OBJECT-TYPE 
        SYNTAX  INTEGER { 
                           other(1), 
                           invalid(2) 
                        } 
        ACCESS  read-write 
        STATUS  mandatory 
        DESCRIPTION 
               "Writing invalid(2) to this object removes the corresponding 
               entry.  When read, this object always returns a value 
               of other(1)." 
    ::= { eauthReadOnlyUserEntry 3 } 
 
    -- 
    -- SNMP Read-Write User Community 
    -- 
 
    eauthReadWriteCommunity OBJECT-TYPE 
        SYNTAX  OCTET STRING (SIZE (32)) 
        ACCESS  read-write 
        STATUS  mandatory 
        DESCRIPTION 
               "The community string used to identify an SNMP community 
               with access rights of Read-Write." 
    ::= { eauth1 5 } 
 
    eauthReadWriteUserTable OBJECT-TYPE 
        SYNTAX  SEQUENCE OF EauthReadWriteUserEntry 
        ACCESS  not-accessible 
        STATUS  mandatory 
        DESCRIPTION 
               "A list of Read-Write users and associated information." 
    ::= { eauth1 6 } 
 
    eauthReadWriteUserEntry OBJECT-TYPE 
        SYNTAX  EauthReadWriteUserEntry 
        ACCESS  not-accessible 
        STATUS  mandatory 
        DESCRIPTION 
               "Objects containing information for a given Read-Write user." 
        INDEX  { eauthReadWriteUserAddr } 
 
 
        ::= { eauthReadWriteUserTable 1 } 
 
    EauthReadWriteUserEntry ::= 
        SEQUENCE { 
            eauthReadWriteUserAddr 
                IpAddress, 
            eauthReadWriteUserMask 
                OCTET STRING, 
            eauthReadWriteUserStatus 
                INTEGER 
                 } 
 
    eauthReadWriteUserAddr OBJECT-TYPE 
        SYNTAX  IpAddress 
        ACCESS  read-write 
        STATUS  mandatory 
        DESCRIPTION 
               "An IP Address, or a set of IP addresses, which has 
               Read-Write SNMP access to this agent.  If this object 
               is used as a wildcard, bits corresponding to the 
               zero bits in the corresponding euthReadWriteUserMask 
               are treated as don't-care." 
    ::= { eauthReadWriteUserEntry 1 } 
 
    eauthReadWriteUserMask OBJECT-TYPE 
        SYNTAX  OCTET STRING (SIZE (4)) 
        ACCESS  read-write 
        STATUS  mandatory 
        DESCRIPTION 
               "A 32-bit mask which is applied to (ANDed with) 
               the source IP address of an incoming SNMP message. 
               If the result of the mask is equal to eauthReadWriteUserAddr, 
               the message is considered to have come from a user 
               who has Read-Write access.  This allows wildcarding, 
               for example, for all NMS's on a given subnet.  For 
               fully specified IP addresses required to be in this 
               community, this mask may be set to all 1's." 
    ::= { eauthReadWriteUserEntry 2 } 
 
    eauthReadWriteUserStatus OBJECT-TYPE 
        SYNTAX  INTEGER { 
                           other(1), 
                           invalid(2) 
                        } 
        ACCESS  read-write 
 
 
        STATUS  mandatory 
        DESCRIPTION 
               "Writing invalid(2) to this object removes the corresponding 
               entry.  When read, this object always returns a value 
               of other(1)." 
    ::= { eauthReadWriteUserEntry 3 } 
 
END
