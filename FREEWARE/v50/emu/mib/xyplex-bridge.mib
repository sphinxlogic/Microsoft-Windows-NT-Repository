XYPLEX-BRIDGE-MIB DEFINITIONS ::= BEGIN

IMPORTS
		enterprises,  Counter, TimeTicks
				FROM RFC1155-SMI
		DisplayString
				FROM RFC1158-MIB;

xyplex	OBJECT IDENTIFIER ::= { enterprises 33 } 

bridge			OBJECT IDENTIFIER ::= { xyplex 5 }

-- the system group

brsys				OBJECT IDENTIFIER ::= { bridge 1 }


brsysName			OBJECT-TYPE			
		SYNTAX	DisplayString (SIZE (0..32))
		ACCESS	read-write
		STATUS	mandatory
		::= { brsys 1 }

brsysMacAddress	OBJECT-TYPE
		SYNTAX	OCTET STRING		-- format ???
		ACCESS	read-only
		STATUS	mandatory
		::= { brsys 2 }

brsysUpTime		OBJECT-TYPE			-- (duplicate of system)
		SYNTAX	TimeTicks
		ACCESS	read-only
		STATUS	mandatory
		::= { brsys 3 }

brsysLatEnhance	OBJECT-TYPE
		SYNTAX	INTEGER { disabled(1), enabled(2) }
		ACCESS	read-write
		STATUS	mandatory
		::= { brsys 4 }

brsysLatAnnceCompTblSize	OBJECT-TYPE
		SYNTAX	INTEGER
		ACCESS	read-write
		STATUS	mandatory
		::= { brsys 5 }

brsysPcktCompTblSize	OBJECT-TYPE
		SYNTAX	INTEGER
		ACCESS	read-write
		STATUS	mandatory
		::= { brsys 6 }

brsysForwardQueueDisc	OBJECT-TYPE
		SYNTAX	Counter
		ACCESS	read-only
		STATUS	mandatory
		::= { brsys 7 }

brsysLocalQueueDisc	OBJECT-TYPE
		SYNTAX	Counter
		ACCESS	read-only
		STATUS	mandatory
		::= { brsys 8 }

brsysVitalinkMacAddress	OBJECT-TYPE
		SYNTAX	OCTET STRING		-- format ???
		ACCESS	read-write
		STATUS	mandatory
		::= { brsys 9 }

brsysLatAnnceCompTblUseSize	OBJECT-TYPE
		SYNTAX	Gauge
		ACCESS	read-only
		STATUS	mandatory
		::= { brsys 10 }

brsysLatAnnceCompTblUseHigh	OBJECT-TYPE
		SYNTAX	Gauge
		ACCESS	read-only
		STATUS	mandatory
		::= { brsys 11 }

brsysPcktCompTblUseSize	OBJECT-TYPE
		SYNTAX	Gauge
		ACCESS	read-only
		STATUS	mandatory
		::= { brsys 12 }

brsysPcktCompTblUseHigh	OBJECT-TYPE
		SYNTAX	Gauge
		ACCESS	read-only
		STATUS	mandatory
		::= { brsys 13 }


-- the stp group

stp				OBJECT IDENTIFIER ::= { bridge 2 }

stpStp			OBJECT-TYPE
		SYNTAX	INTEGER { disabled(1), enabled(2) }
		ACCESS	read-write
		STATUS	mandatory
		::= { stp 1 }

stpForwardTimer	OBJECT-TYPE
		SYNTAX	INTEGER (1..3600)	-- in seconds
		ACCESS	read-write
		STATUS	mandatory
		::= { stp 2 }

stpHelloTimer	OBJECT-TYPE
		SYNTAX	INTEGER (1..3600)	-- in seconds
		ACCESS	read-write
		STATUS	mandatory
		::= { stp 3 }

stpMaxAgeTimer	OBJECT-TYPE
		SYNTAX	INTEGER (1..3600)	-- in seconds
		ACCESS	read-write
		STATUS	mandatory
		::= { stp 4 }

stpMulticastAddress	OBJECT-TYPE
		SYNTAX	OCTET STRING		-- format ???
		ACCESS	read-write
		STATUS	mandatory
		::= { stp 5 }

stpPriority		OBJECT-TYPE
		SYNTAX	INTEGER (0..255)
		ACCESS	read-write
		STATUS	mandatory
		::= { stp 6 }

stpTopChngTimer	OBJECT-TYPE
		SYNTAX	INTEGER	 			-- in seconds
		ACCESS	read-only
		STATUS	mandatory
		::= { stp 7 }

stpDesigRoot	OBJECT-TYPE
		SYNTAX	OCTET STRING		-- format ???
		ACCESS	read-only
		STATUS	mandatory
		::= { stp 8 }

stpDesigRootCost	OBJECT-TYPE
		SYNTAX	INTEGER
		ACCESS	read-only
		STATUS	mandatory
		::= { stp 9 }

stpDesigForwardTimer	OBJECT-TYPE
		SYNTAX	INTEGER				-- in seconds
		ACCESS	read-only
		STATUS	mandatory
		::= { stp 10 }

stpDesigHelloTimer	OBJECT-TYPE
		SYNTAX	INTEGER				-- in seconds
		ACCESS	read-only
		STATUS	mandatory
		::= { stp 11 }

stpDesigMaxAgeTimer	OBJECT-TYPE
		SYNTAX	INTEGER				-- in seconds
		ACCESS	read-only
		STATUS	mandatory
		::= { stp 12 }

stpDesigRootLink	OBJECT-TYPE
		SYNTAX	INTEGER
		ACCESS	read-only
		STATUS	mandatory
		::= { stp 13 }

stpDesigRootPriority	OBJECT-TYPE
		SYNTAX	INTEGER
		ACCESS	read-only
		STATUS	mandatory
		::= { stp 14 }

stpTopChngCount	OBJECT-TYPE
		SYNTAX	Gauge
		ACCESS	read-only
		STATUS	mandatory
		::= { stp 15 }

stpTopStableTime	OBJECT-TYPE
		SYNTAX	TimeTicks
		ACCESS	read-only
		STATUS	mandatory
		::= { stp 16 }

stpTopState	OBJECT-TYPE
		SYNTAX	INTEGER { stable(1), changing(2) }
		ACCESS	read-only
		STATUS	mandatory
		::= { stp 17 }

stpNumLinks	OBJECT-TYPE
		SYNTAX	Counter
		ACCESS	read-only
		STATUS	mandatory
		::= { stp 18 }

stpLinkTbl	OBJECT-TYPE
		SYNTAX	SEQUENCE OF StpLinkTblEnt
		ACCESS	not-accessible
		STATUS	mandatory
		::= { stp 19 }
		
stpLinkTblEnt	OBJECT-TYPE
		SYNTAX	StpLinkTblEnt
		ACCESS	not-accessible
		STATUS	mandatory
		::= { stpLinkTbl 1 }

StpLinkTblEnt	::= SEQUENCE {
			stpLinkID
				INTEGER,
			stpLinkMacAddress
				OCTET STRING,
			stpLinkPriority
				INTEGER,
			stpLinkPathcost
				INTEGER,
			stpLinkPathcostCur
				INTEGER,
			stpLinkPathcostWeighted
				INTEGER,
			stpLinkState
				INTEGER,
			stpLinkDesigRoot
				OCTET STRING,
			stpLinkDesigCost
				INTEGER,
			stpLinkDesigBridge
				OCTET STRING,
			stpLinkDesigLink
				INTEGER,
			stpLinkTopChngAck
				INTEGER
		}

stpLinkID	OBJECT-TYPE
		SYNTAX	INTEGER
		ACCESS	read-only
		STATUS	mandatory
		::= { stpLinkTblEnt 1 }

stpLinkMacAddress	OBJECT-TYPE
		SYNTAX	OCTET STRING			-- format ??
		ACCESS	read-only
		STATUS	mandatory
		::= { stpLinkTblEnt 2 }

stpLinkpriority	OBJECT-TYPE
		SYNTAX	INTEGER (0..255)
		ACCESS	read-write
		STATUS	mandatory
		::= { stpLinkTblEnt 3 }

stpLinkPathcost	OBJECT-TYPE
		SYNTAX	INTEGER (0..65534) -- { Auto(65535) }
		ACCESS	read-write
		STATUS	mandatory
		::= { stpLinkTblEnt 4 }

stpLinkPathcostCur	OBJECT-TYPE
		SYNTAX	INTEGER
		ACCESS	read-only
		STATUS	mandatory
		::= { stpLinkTblEnt 5 }

stpLinkPathcostWeighted	OBJECT-TYPE
		SYNTAX	INTEGER  { disabled(1), enabled(2) }
		ACCESS	read-write
		STATUS	mandatory
		::= { stpLinkTblEnt 6 }

stpLinkState	OBJECT-TYPE
		SYNTAX	INTEGER { disabled(1), blocked(2), forwarding(3), learning(4), listening(5) }
		ACCESS	read-write
		STATUS	mandatory
		::= { stpLinkTblEnt 7 }

stpLinkDesigRoot	OBJECT-TYPE
		SYNTAX	OCTET STRING			-- format ??
		ACCESS	read-only
		STATUS	mandatory
		::= { stpLinkTblEnt 8 }

stpLinkDesigCost	OBJECT-TYPE
		SYNTAX	INTEGER
		ACCESS	read-only
		STATUS	mandatory
		::= { stpLinkTblEnt 9 }

stpLinkDesigBridge	OBJECT-TYPE
		SYNTAX	OCTET STRING			-- format ??
		ACCESS	read-only
		STATUS	mandatory
		::= { stpLinkTblEnt 10 }

stpLinkDesigLink	OBJECT-TYPE
		SYNTAX	INTEGER
		ACCESS	read-only
		STATUS	mandatory
		::= { stpLinkTblEnt 11 }

stpLinkTopChngAck	OBJECT-TYPE
		SYNTAX	INTEGER { notAcknowledged(1), acknowledged(2) }
		ACCESS	read-only
		STATUS	mandatory
		::= { stpLinkTblEnt 12 }

stpMaxForwardDelay	OBJECT-TYPE
		SYNTAX	INTEGER -- { none(0) }	 otherwise milliseconds
		ACCESS	read-write
		STATUS	mandatory
		::= { stp 20 }

stpMaxMultiForwardDelay	OBJECT-TYPE		-- multicast delay
		SYNTAX	INTEGER --{ none(0) }	otherwise milliseconds
		ACCESS	read-write
		STATUS	mandatory
		::= { stp 21 }

stpEarlyLoopDetection	OBJECT-TYPE	
		SYNTAX	INTEGER { disabled(1), enabled(2) }
		ACCESS	read-write
		STATUS	mandatory
		::= { stp 22 }

stpEarlyLoopCount	OBJECT-TYPE	
		SYNTAX	Counter
		ACCESS	read-only
		STATUS	mandatory
		::= { stp 23 }


-- the filters group

fl			OBJECT IDENTIFIER ::= { bridge 3 }

flFiltering	OBJECT-TYPE
		SYNTAX	INTEGER { disabled(1), enabled(2) }
		ACCESS	read-write
		STATUS	mandatory
		::= { fl 1 }

flTableSize	OBJECT-TYPE
		SYNTAX	INTEGER (10..4000)
		ACCESS	read-write
		STATUS	mandatory
		::= { fl 2 }

flDiscardTimeout	OBJECT-TYPE
		SYNTAX	INTEGER (0..65535)		-- in seconds
		ACCESS	read-write
		STATUS	mandatory
		::= { fl 3 }

flUseTimeout	OBJECT-TYPE
		SYNTAX	INTEGER (0..65535)		-- in seconds
		ACCESS	read-write
		STATUS	mandatory
		::= { fl 4 }

flSrcNumSourceCur	OBJECT-TYPE
		SYNTAX	Gauge
		ACCESS	read-only
		STATUS	mandatory
		::= { fl 5 }

flSrcNumSourceHigh	OBJECT-TYPE
		SYNTAX	Gauge
		ACCESS	read-only
		STATUS	mandatory
		::= { fl 6 }

flSrcNumSourceMax	OBJECT-TYPE
		SYNTAX	Gauge
		ACCESS	read-only
		STATUS	mandatory
		::= { fl 7 }

flSrcFilterTbl	OBJECT-TYPE
		SYNTAX	SEQUENCE OF FlSrcFilterTblEnt
		ACCESS	not-accessible
		STATUS	mandatory
		::= { fl 8 }
		
flSrcFilterTblEnt	OBJECT-TYPE
		SYNTAX	FlSrcFilterTblEnt
		ACCESS	not-accessible
		STATUS	mandatory
		::= { flSrcFilterTbl 1 }

FlSrcFilterTblEnt	::= SEQUENCE {
			flSrcEntID
				INTEGER,
			flSrcEntMacAddress
				OCTET STRING,
			flSrcEntForwardFlag
				INTEGER,
			flSrcEntUseCount
				Counter
		}

flSrcEntID	OBJECT-TYPE
		SYNTAX	INTEGER
		ACCESS	read-only
		STATUS	mandatory
		::= { flSrcFilterTblEnt 1 }

flSrcEntMacAddress	OBJECT-TYPE
		SYNTAX	OCTET STRING			-- format ???
		ACCESS	read-write
		STATUS	mandatory
		::= { flSrcFilterTblEnt 2 }

flSrcEntForwardFlag	OBJECT-TYPE
		SYNTAX	INTEGER { discard(1), forward(2) }
		ACCESS	read-write
		STATUS	mandatory
		::= { flSrcFilterTblEnt 3 }

flSrcEntUseCount	OBJECT-TYPE
		SYNTAX	Counter
		ACCESS	read-only
		STATUS	mandatory
		::= { flSrcFilterTblEnt 4 }

flDstInactiveNumCur	OBJECT-TYPE
		SYNTAX	Gauge
		ACCESS	read-only
		STATUS	mandatory
		::= { fl 9 }

flDstInactiveNumHigh	OBJECT-TYPE
		SYNTAX	Gauge 
		ACCESS	read-only
		STATUS	mandatory
		::= { fl 10 }

flDstInactiveNumMax	OBJECT-TYPE
		SYNTAX	Gauge 
		ACCESS	read-only
		STATUS	mandatory
		::= { fl 11 }

flDstLearnedNumCur	OBJECT-TYPE
		SYNTAX	Gauge 
		ACCESS	read-only
		STATUS	mandatory
		::= { fl 12 }

flDstLearnedNumHigh	OBJECT-TYPE
		SYNTAX	Gauge 
		ACCESS	read-only
		STATUS	mandatory
		::= { fl 13 }

flDstLearnedNumMax	OBJECT-TYPE
		SYNTAX	Gauge 
		ACCESS	read-only
		STATUS	mandatory
		::= { fl 14 }

flDstLearnedNumErrors	OBJECT-TYPE
		SYNTAX	Counter
		ACCESS	read-only
		STATUS	mandatory
		::= { fl 15 }

flDstStaticNumCur	OBJECT-TYPE
		SYNTAX	Gauge 
		ACCESS	read-only
		STATUS	mandatory
		::= { fl 16 }

flDstStaticNumHigh	OBJECT-TYPE
		SYNTAX	Gauge 
		ACCESS	read-only
		STATUS	mandatory
		::= { fl 17 }

flDstStaticNumMax	OBJECT-TYPE
		SYNTAX	Gauge 
		ACCESS	read-only
		STATUS	mandatory
		::= { fl 18 }

flDstFilterTbl	OBJECT-TYPE
		SYNTAX	SEQUENCE OF FlDstFilterTblEnt
		ACCESS	not-accessible
		STATUS	mandatory
		::= { fl 19 }
		
flDstFilterTblEnt	OBJECT-TYPE
		SYNTAX	FlDstFilterTblEnt
		ACCESS	not-accessible
		STATUS	mandatory
		::= { flDstFilterTbl 1 }

FlDstFilterTblEnt	::= SEQUENCE {
			flDstEntID
				INTEGER,
			flDstEntMacAddress
				OCTET STRING,
			flDstEntLinkMap
				OCTET STRING,
			flDstEntStatus
				INTEGER,
			flDstEntTtl
				Gauge,
			flDstEntUseCount
				Counter
		}

flDstEntID	OBJECT-TYPE
		SYNTAX	INTEGER
		ACCESS	read-only
		STATUS	mandatory
		::= { flDstFilterTblEnt 1 }

flDstEntMacAddress	OBJECT-TYPE
		SYNTAX	OCTET STRING			-- format ???
		ACCESS	read-write
		STATUS	mandatory
		::= { flDstFilterTblEnt 2 }

flDstEntLinkMap	OBJECT-TYPE
		SYNTAX	OCTET STRING			-- bit map of links to forward to
		ACCESS	read-write
		STATUS	mandatory
		::= { flDstFilterTblEnt 3 }

flDstEntStatus	OBJECT-TYPE
		SYNTAX	INTEGER { static(1), learned(2), inactive(3) }
		ACCESS	read-write
		STATUS	mandatory
		::= { flDstFilterTblEnt 4 }

flDstEntTtl	OBJECT-TYPE
		SYNTAX	Gauge
		ACCESS	read-write
		STATUS	mandatory
		::= { flDstFilterTblEnt 5 }

flDstEntUseCount	OBJECT-TYPE
		SYNTAX	Counter
		ACCESS	read-only
		STATUS	mandatory
		::= { flDstFilterTblEnt 6 }

flLinkTbl	OBJECT-TYPE
		SYNTAX	SEQUENCE OF FlLinkTblEnt
		ACCESS	not-accessible
		STATUS	mandatory
		::= { fl 20 }
		
flLinkTblEnt	OBJECT-TYPE
		SYNTAX	FlLinkTblEnt
		ACCESS	not-accessible
		STATUS	mandatory
		::= { flLinkTbl 1 }

FlLinkTblEnt	::= SEQUENCE {
			flLinkEntID
				INTEGER,
			flLinkEntLearning
				INTEGER
		}

flLinkEntID	OBJECT-TYPE
		SYNTAX	INTEGER
		ACCESS	read-only
		STATUS	mandatory
		::= { flLinkTblEnt 1 }

flLinkEntLearning	OBJECT-TYPE
		SYNTAX	INTEGER { disabled(1), enabled(2) }
		ACCESS	read-write
		STATUS	mandatory
		::= { flLinkTblEnt 2 }


-- the protocols group

prtcl		OBJECT IDENTIFIER ::= { bridge 4 }

prtclProtocol	OBJECT-TYPE
		SYNTAX	INTEGER { disabled(1), enabled(2) }
		ACCESS	read-write
		STATUS	mandatory
		::= { prtcl 1 }

prtclNumCur	OBJECT-TYPE
		SYNTAX	Gauge
		ACCESS	read-only
		STATUS	mandatory
		::= { prtcl 2 }

prtclNumMax	OBJECT-TYPE
		SYNTAX	Gauge
		ACCESS	read-only
		STATUS	mandatory
		::= { prtcl 3 }

prtclTbl	OBJECT-TYPE
		SYNTAX	SEQUENCE OF PrtclTblEnt
		ACCESS	not-accessible
		STATUS	mandatory
		::= { prtcl 4 }
		
prtclTblEnt	OBJECT-TYPE
		SYNTAX	PrtclTblEnt
		ACCESS	not-accessible
		STATUS	mandatory
		::= { prtclTbl 1 }

PrtclTblEnt	::= SEQUENCE {
			prtclEntID
				INTEGER,
			prtclEntProtocolID
				INTEGER,
			prtclEntMac
				INTEGER,
			prtclEntName
				DisplayString,
			prtclEntPriority
				INTEGER,
			prtclEntUseCount
				Counter
		}

prtclEntID	OBJECT-TYPE
		SYNTAX	INTEGER
		ACCESS	read-only
		STATUS	mandatory
		::= { prtclTblEnt 1 }

prtclEntProtocolID	OBJECT-TYPE		-- mac ID is mac is True; else N/A
		SYNTAX	INTEGER
		ACCESS	read-write
		STATUS	mandatory
		::= { prtclTblEnt 2 }

prtclEntMac	OBJECT-TYPE
		SYNTAX	INTEGER { non-Mac(1), mac(2) }
		ACCESS	read-write
		STATUS	mandatory
		::= { prtclTblEnt 3 }

prtclEntName	OBJECT-TYPE
		SYNTAX	DisplayString (SIZE (0..24))
		ACCESS	read-write
		STATUS	mandatory
		::= { prtclTblEnt 4 }

prtclEntPriority	OBJECT-TYPE
		SYNTAX	INTEGER { low(1), medium(3), high(5), discard(101) }
		ACCESS	read-write
		STATUS	mandatory
		::= { prtclTblEnt 5 }

prtclEntUseCount	OBJECT-TYPE
		SYNTAX	Counter
		ACCESS	read-only
		STATUS	mandatory
		::= { prtclTblEnt 6 }

prtclDefaultPriority	OBJECT-TYPE
		SYNTAX	INTEGER { low(1), medium(3), high(5), discard(101) }
		ACCESS	read-write
		STATUS	mandatory
		::= { prtcl 5 }

prtclDefaultUseCount	OBJECT-TYPE
		SYNTAX	Counter
		ACCESS	read-only
		STATUS	mandatory
		::= { prtcl 6 }


-- the links group

lks		OBJECT IDENTIFIER ::= { bridge 5 }

lksNum	OBJECT-TYPE
		SYNTAX	Counter
		ACCESS	read-only
		STATUS	mandatory
		::= { lks 1 }

lksTbl	OBJECT-TYPE
		SYNTAX	SEQUENCE OF LksTblEnt
		ACCESS	not-accessible
		STATUS	mandatory
		::= { lks 2 }
		
lksTblEnt OBJECT-TYPE
		SYNTAX	LksTblEnt
		ACCESS	not-accessible
		STATUS	mandatory
		::= { lksTbl 1 }

LksTblEnt	::= SEQUENCE {
			lksEntID
				INTEGER,
			lksEntStateConfig
				INTEGER,
			lksEntStateActive
				INTEGER,
			lksEntType
				INTEGER,
			lksEntTypeSpecific
				OBJECT IDENTIFIER,
			lksEntName
				DisplayString,
			lksEntUtilizationCur
				Gauge,
			lksEntUtilizationHigh
				Gauge,
			lksEntUtilizationAvg
				Gauge,
			lksEntForwardingCur
				Gauge,
			lksEntForwardingHigh
				Gauge,
			lksEntForwardingAvg
				Gauge,
			lksEntFilteringCur
				Gauge,
			lksEntFilteringHigh
				Gauge,
			lksEntFilteringAvg
				Gauge,
			lksEntOutputQCur
				Gauge,
			lksEntOutputQHigh
				Gauge,
			lksEntOutputQTotal
				Gauge,
			lksEntTransmitLinkSpeed
				Gauge,
			lksEntReceiveLinkSpeed
				Gauge,
			lksEntTraffic
				OBJECT IDENTIFIER,
			lksEntDiscards
				OBJECT IDENTIFIER
		}

lksEntID	OBJECT-TYPE
		SYNTAX	INTEGER
		ACCESS	read-only
		STATUS	mandatory
		::= { lksTblEnt 1 }

-- standby is not supported in the first pass
lksEntStateConfig	OBJECT-TYPE
		SYNTAX	INTEGER { disabled(1), enabled(2), standby(3) }
		ACCESS	read-write
		STATUS	mandatory
		::= { lksTblEnt 2 }

lksEntStateActive	OBJECT-TYPE
		SYNTAX	INTEGER { initWaitDSR(129), initWait(130), down1(132),down(135), purging1(133), purging(136), running1(131), running(134), loop(136), testSend(138), testReceive(139), testLoop(140) }
		ACCESS	read-only
		STATUS	mandatory
		::= { lksTblEnt 3 }

lksEntType	OBJECT-TYPE
		SYNTAX	INTEGER { unknown(1), wan(3), lan(4) }	-- Undefined is UNKNOWN
		ACCESS	read-only
		STATUS	mandatory
		::= { lksTblEnt 4 }

lksEntTypeSpecific	OBJECT-TYPE
		SYNTAX	OBJECT IDENTIFIER
		ACCESS	read-only
		STATUS	mandatory
		::= { lksTblEnt 5 }

lksEntName	OBJECT-TYPE
		SYNTAX	DisplayString (SIZE (0..25))
		ACCESS	read-write
		STATUS	mandatory
		::= { lksTblEnt 6 }

lksEntUtilizationCur	OBJECT-TYPE
		SYNTAX	Gauge
		ACCESS	read-only
		STATUS	mandatory
		::= { lksTblEnt 7 }

lksEntUtilizationHigh	OBJECT-TYPE
		SYNTAX	Gauge
		ACCESS	read-only
		STATUS	mandatory
		::= { lksTblEnt 8 }

lksEntUtilizationAvg	OBJECT-TYPE
		SYNTAX	Gauge
		ACCESS	read-only
		STATUS	mandatory
		::= { lksTblEnt 9 }

lksEntForwardingCur	OBJECT-TYPE
		SYNTAX	Gauge
		ACCESS	read-only
		STATUS	mandatory
		::= { lksTblEnt 10 }

lksEntForwardingHigh	OBJECT-TYPE
		SYNTAX	Gauge
		ACCESS	read-only
		STATUS	mandatory
		::= { lksTblEnt 11 }

lksEntForwardingAvg	OBJECT-TYPE
		SYNTAX	Gauge
		ACCESS	read-only
		STATUS	mandatory
		::= { lksTblEnt 12 }

lksEntFilteringCur	OBJECT-TYPE
		SYNTAX	Gauge
		ACCESS	read-only
		STATUS	mandatory
		::= { lksTblEnt 13 }

lksEntFilteringHigh	OBJECT-TYPE
		SYNTAX	Gauge
		ACCESS	read-only
		STATUS	mandatory
		::= { lksTblEnt 14 }

lksEntFilteringAvg	OBJECT-TYPE
		SYNTAX	Gauge
		ACCESS	read-only
		STATUS	mandatory
		::= { lksTblEnt 15 }

lksEntOutputQCur	OBJECT-TYPE
		SYNTAX	Gauge
		ACCESS	read-only
		STATUS	mandatory
		::= { lksTblEnt 16 }

lksEntOutputQHigh	OBJECT-TYPE
		SYNTAX	Gauge
		ACCESS	read-only
		STATUS	mandatory
		::= { lksTblEnt 17 }

lksEntOutputQTotal	OBJECT-TYPE
		SYNTAX	Gauge
		ACCESS	read-only
		STATUS	mandatory
		::= { lksTblEnt 18 }

lksEntTransmitLinkSpeed	OBJECT-TYPE
		SYNTAX	Gauge
		ACCESS	read-only
		STATUS	mandatory
		::= { lksTblEnt 19 }

lksEntReceiveLinkSpeed	OBJECT-TYPE
		SYNTAX	Gauge
		ACCESS	read-only
		STATUS	mandatory
		::= { lksTblEnt 20 }

lksEntTraffic	OBJECT IDENTIFIER ::= { lksTblEnt 21 }

lksEntTrafficPacketsIn OBJECT-TYPE
		SYNTAX	Counter
		ACCESS	read-only
		STATUS	mandatory
		::= { lksEntTraffic 1 }

lksEntTrafficPacketsOut OBJECT-TYPE
		SYNTAX	Counter
		ACCESS	read-only
		STATUS	mandatory
		::= { lksEntTraffic 2 }

lksEntTrafficMulticastsIn OBJECT-TYPE
		SYNTAX	Counter
		ACCESS	read-only
		STATUS	mandatory
		::= { lksEntTraffic 3 }

lksEntTrafficMulticastsOut OBJECT-TYPE
		SYNTAX	Counter
		ACCESS	read-only
		STATUS	mandatory
		::= { lksEntTraffic 4 }

lksEntTrafficUnicastsIn OBJECT-TYPE
		SYNTAX	Counter
		ACCESS	read-only
		STATUS	mandatory
		::= { lksEntTraffic 5 }

lksEntTrafficUnicastsOut OBJECT-TYPE
		SYNTAX	Counter
		ACCESS	read-only
		STATUS	mandatory
		::= { lksEntTraffic 6 }

lksEntTrafficStpIn OBJECT-TYPE
		SYNTAX	Counter
		ACCESS	read-only
		STATUS	mandatory
		::= { lksEntTraffic 7 }

lksEntTrafficStpOut OBJECT-TYPE
		SYNTAX	Counter
		ACCESS	read-only
		STATUS	mandatory
		::= { lksEntTraffic 8 }

lksEntTrafficBytesIn OBJECT-TYPE
		SYNTAX	Counter
		ACCESS	read-only
		STATUS	mandatory
		::= { lksEntTraffic 9 }

lksEntTrafficBytesOut OBJECT-TYPE
		SYNTAX	Counter
		ACCESS	read-only
		STATUS	mandatory
		::= { lksEntTraffic 10 }

lksEntDiscards	OBJECT IDENTIFIER ::= { lksTblEnt 22 }

lksEntDiscardCrcError OBJECT-TYPE
		SYNTAX	Counter
		ACCESS	read-only
		STATUS	mandatory
		::= { lksEntDiscards 1 }

lksEntDiscardFiltering OBJECT-TYPE
		SYNTAX	Counter
		ACCESS	read-only
		STATUS	mandatory
		::= { lksEntDiscards 2 }

lksEntDiscardnoBuffers OBJECT-TYPE
		SYNTAX	Counter
		ACCESS	read-only
		STATUS	mandatory
		::= { lksEntDiscards 3 }

lksEntDiscardPriority OBJECT-TYPE
		SYNTAX	Counter
		ACCESS	read-only
		STATUS	mandatory
		::= { lksEntDiscards 4 }

lksEntDiscardLatGroupAnnce OBJECT-TYPE
		SYNTAX	Counter
		ACCESS	read-only
		STATUS	mandatory
		::= { lksEntDiscards 5 }

lksEntDiscardLostBuffers OBJECT-TYPE
		SYNTAX	Counter
		ACCESS	read-only
		STATUS	mandatory
		::= { lksEntDiscards 6 }

lksEntDiscardOutputQueueFull OBJECT-TYPE
		SYNTAX	Counter
		ACCESS	read-only
		STATUS	mandatory
		::= { lksEntDiscards 7 }

lksEntDiscardDelayExceeded OBJECT-TYPE
		SYNTAX	Counter
		ACCESS	read-only
		STATUS	mandatory
		::= { lksEntDiscards 8 }


-- the wan group

wan		OBJECT IDENTIFIER ::= { bridge 6 }

wanNullClock	OBJECT-TYPE
		SYNTAX	INTEGER 	-- 0, 8.333k, 66.667k, 250k, 2M
		ACCESS	read-write
		STATUS	mandatory
		::= { wan 1 }

wanNum	OBJECT-TYPE
		SYNTAX	Counter
		ACCESS	read-only
		STATUS	mandatory
		::= { wan 2 }

wanTbl	OBJECT-TYPE
		SYNTAX	SEQUENCE OF WanTblEnt
		ACCESS	not-accessible
		STATUS	mandatory
		::= { wan 3 }

wanTblEnt	OBJECT-TYPE
		SYNTAX	WanTblEnt
		ACCESS	not-accessible
		STATUS	mandatory
		::= { wanTbl 1 }

WanTblEnt	::= SEQUENCE {
			wanEntID
				INTEGER,
			wanEntCompression
				INTEGER,
			wanEntDsrTimeout
				INTEGER,
-- next field is not supported first pass
			wanEntLocalPhone
				DisplayString,
-- next field is not supported first pass
			wanEntDialPhoneNumMax
				INTEGER,
-- next field is not supported first pass
--			wanEntDialPhoneTbl
--				SEQUENCE OF LksEntDialPhoneEnt,
			wanEntGroups
				OCTET STRING,
-- next field is not supported first pass
			wanEntModemType
				INTEGER,
			wanEntNullClock
-- depricated field
				INTEGER,
			wanEntPathcostWeighted
				INTEGER,
			wanEntErrorRateCur
				Gauge,
			wanEntErrorRateHigh
				Gauge,
			wanEntErrorRateAvg
				Gauge,
			wanEntLinkDownCur
				Gauge,
			wanEntLinkDownHigh
				Gauge,
			wanEntLinkDownTotal
				Counter,
			wanEntLinkDownCount
				Counter,
			wanEntCableType
				INTEGER,
			wanEntCtsCur
				INTEGER,
			wanEntRtsCur
				INTEGER,
			wanEntDcdCur
				INTEGER,
			wanEntDsrCur
				INTEGER,
			wanEntDtrCur
				INTEGER,
			wanEntRingCur
				INTEGER,
			wanEntCtsChanges
				Counter,
			wanEntRtsChanges
				Counter,
			wanEntDcdChanges
				Counter,
			wanEntDsrChanges
				Counter,
			wanEntDtrChanges
				Counter,
			wanEntRingChanges
				Counter,
			wanEntCompNum
				Counter,
			wanEntCompressionTbl
				WanEntCompEnt,
			wanEntCompressionStatus
				INTEGER
		}

wanEntID	OBJECT-TYPE
		SYNTAX	INTEGER
		ACCESS	read-only
		STATUS	mandatory
		::= { wanTblEnt 1 }

wanEntCompression	OBJECT-TYPE
		SYNTAX	INTEGER { enabled(1), disabled(2), auto(256) }
		ACCESS	read-write
		STATUS	mandatory
		::= { wanTblEnt 2 }

wanEntDsrTimeout	OBJECT-TYPE
		SYNTAX	INTEGER (0..1000)
		ACCESS	read-write
		STATUS	mandatory
		::= { wanTblEnt 3 }

-- next field is not supported first pass
wanEntLocalPhone	OBJECT-TYPE
		SYNTAX	DisplayString (SIZE (0..25))	-- a dialable string passed to modem
		ACCESS	read-write
		STATUS	mandatory
		::= { wanTblEnt 4 }

-- next field is not supported first pass
wanEntDialPhoneNumMax OBJECT-TYPE
		SYNTAX	INTEGER
		ACCESS	read-only
		STATUS	mandatory
		::= { wanTblEnt 5 }

-- next field is not supported first pass
wanEntDialPhoneTbl	OBJECT-TYPE
		SYNTAX	SEQUENCE OF WanEntDialPhoneEnt
		ACCESS	not-accessible
		STATUS	mandatory
		::= { wanTblEnt 6 }

-- next field is not supported first pass
wanEntDialPhoneEnt OBJECT-TYPE
		SYNTAX	WanEntDialPhoneEnt
		ACCESS	not-accessible
		STATUS	mandatory
		::= { wanEntDialPhoneTbl 1 }

-- next field is not supported first pass
WanEntDialPhoneEnt	::= SEQUENCE {
			wanEntDialPhoneEntID
				INTEGER,
			wanEntDialPhoneEntPhone
				DisplayString
		}

-- next field is not supported first pass
wanEntDialPhoneEntID	OBJECT-TYPE
		SYNTAX	INTEGER
		ACCESS	read-only
		STATUS	mandatory
		::= { wanEntDialPhoneEnt 1 }

-- next field is not supported first pass
wanEntDialPhoneEntPhone	OBJECT-TYPE
		SYNTAX	DisplayString (SIZE (0..25))	-- a dialable string passed to modem
		ACCESS	read-write
		STATUS	mandatory
		::= { wanEntDialPhoneEnt 2 }

wanEntGroups	OBJECT-TYPE
		SYNTAX	OCTET STRING		-- 256 bit map of the groups which are enabled
		ACCESS	read-write
		STATUS	mandatory
		::= { wanTblEnt 7 }

-- next field is not supported first pass
wanEntModemType	OBJECT-TYPE
		SYNTAX	INTEGER { dedicated(1), dialUp(2) }
		ACCESS	read-write
		STATUS	mandatory
		::= { wanTblEnt 8 }

wanEntNullClock	OBJECT-TYPE
		SYNTAX	INTEGER { enabled(1), disabled(2) }
		ACCESS	read-write
		STATUS	mandatory
		::= { wanTblEnt 9 }

wanEntPathcostWeighted	OBJECT-TYPE
		SYNTAX	INTEGER { enabled(1), disabled(2) }
		ACCESS	read-write
		STATUS	mandatory
		::= { wanTblEnt 10 }

wanEntErrorRateCur	OBJECT-TYPE
		SYNTAX	Gauge
		ACCESS	read-only
		STATUS	mandatory
		::= { wanTblEnt 11 }

wanEntErrorRateHigh	OBJECT-TYPE
		SYNTAX	Gauge
		ACCESS	read-only
		STATUS	mandatory
		::= { wanTblEnt 12 }

wanEntErrorRateAvg	OBJECT-TYPE
		SYNTAX	Gauge
		ACCESS	read-only
		STATUS	mandatory
		::= { wanTblEnt 13 }

wanEntLinkDownCur	OBJECT-TYPE
		SYNTAX	Gauge
		ACCESS	read-only
		STATUS	mandatory
		::= { wanTblEnt 14 }

wanEntLinkDownHigh	OBJECT-TYPE
		SYNTAX	Gauge
		ACCESS	read-only
		STATUS	mandatory
		::= { wanTblEnt 15 }

wanEntLinkDownTotal	OBJECT-TYPE
		SYNTAX	Counter
		ACCESS	read-only
		STATUS	mandatory
		::= { wanTblEnt 16 }

wanEntLinkDownCount	OBJECT-TYPE
		SYNTAX	Counter
		ACCESS	read-only
		STATUS	mandatory
		::= { wanTblEnt 17 }

wanEntCableType	OBJECT-TYPE
		SYNTAX	INTEGER { cable422(1), cable423(2), cableV35(3), unknown(4) }
		ACCESS	read-only
		STATUS	mandatory
		::= { wanTblEnt 18 }

wanEntCtsCur	OBJECT-TYPE
		SYNTAX	INTEGER { no(1), observed(2) }
		ACCESS	read-only
		STATUS	mandatory
		::= { wanTblEnt 19 }

wanEntRtsCur	OBJECT-TYPE
		SYNTAX	INTEGER { no(1), asserted(2) }
		ACCESS	read-only
		STATUS	mandatory
		::= { wanTblEnt 20 }

wanEntDcdCur	OBJECT-TYPE
		SYNTAX	INTEGER { no(1), observed(2) }
		ACCESS	read-only
		STATUS	mandatory
		::= { wanTblEnt 21 }

wanEntDsrCur	OBJECT-TYPE
		SYNTAX	INTEGER { no(1), observed(2) }
		ACCESS	read-only
		STATUS	mandatory
		::= { wanTblEnt 22 }

wanEntDtrCur	OBJECT-TYPE
		SYNTAX	INTEGER { no(1), asserted(2) }
		ACCESS	read-only
		STATUS	mandatory
		::= { wanTblEnt 23 }

wanEntRingCur	OBJECT-TYPE
		SYNTAX	INTEGER { no(1), observed(2) }
		ACCESS	read-only
		STATUS	mandatory
		::= { wanTblEnt 24 }

wanEntCtsChanges	OBJECT-TYPE
		SYNTAX	Counter
		ACCESS	read-only
		STATUS	mandatory
		::= { wanTblEnt 25 }

wanEntRtsChanges	OBJECT-TYPE
		SYNTAX	Counter
		ACCESS	read-only
		STATUS	mandatory
		::= { wanTblEnt 26 }

wanEntDcdChanges	OBJECT-TYPE
		SYNTAX	Counter
		ACCESS	read-only
		STATUS	mandatory
		::= { wanTblEnt 27 }

wanEntDsrChanges	OBJECT-TYPE
		SYNTAX	Counter
		ACCESS	read-only
		STATUS	mandatory
		::= { wanTblEnt 28 }

wanEntDtrChanges	OBJECT-TYPE
		SYNTAX	Counter
		ACCESS	read-only
		STATUS	mandatory
		::= { wanTblEnt 29 }

wanEntRingChanges	OBJECT-TYPE
		SYNTAX	Counter
		ACCESS	read-only
		STATUS	mandatory
		::= { wanTblEnt 30 }

wanEntCompNum	OBJECT-TYPE
		SYNTAX	Counter
		ACCESS	read-only
		STATUS	mandatory
		::= { wanTblEnt 31 }

wanEntCompressionTbl	OBJECT-TYPE
		SYNTAX	SEQUENCE OF WanEntCompEnt
		ACCESS	not-accessible
		STATUS	mandatory
		::= { wanTblEnt 32 }

wanEntCompEnt	OBJECT-TYPE
		SYNTAX	WanEntCompEnt
		ACCESS	not-accessible
		STATUS	mandatory
		::= { wanEntCompressionTbl 1 }

WanEntCompEnt	::= SEQUENCE {
			wanEntCompEntID
				INTEGER,
			wanEntCompEntDescription
				DisplayString,
			wanEntCompEntCurrent
				Gauge,
			wanEntCompEntHigh
				Gauge,
			wanEntCompEntAverage
				Gauge
		}

wanEntCompEntID OBJECT-TYPE
		SYNTAX	INTEGER
		ACCESS	read-only
		STATUS	mandatory
		::= { wanEntCompEnt 1 }

wanEntCompEntDescription OBJECT-TYPE
		SYNTAX	DisplayString
		ACCESS	read-only
		STATUS	mandatory
		::= { wanEntCompEnt 2 }

wanEntCompEntCurrent OBJECT-TYPE
		SYNTAX	Gauge
		ACCESS	read-only
		STATUS	mandatory
		::= { wanEntCompEnt 3 }

wanEntCompEntHigh OBJECT-TYPE
		SYNTAX	Gauge
		ACCESS	read-only
		STATUS	mandatory
		::= { wanEntCompEnt 4 }

wanEntCompEntAverage OBJECT-TYPE
		SYNTAX	Gauge
		ACCESS	read-only
		STATUS	mandatory
		::= { wanEntCompEnt 5 }

wanEntCompressionStatus	OBJECT-TYPE
		SYNTAX	INTEGER { enabled(1), disabled(2) }
		ACCESS	read-only
		STATUS	mandatory
		::= { wanTblEnt 33 }

wanVitalinkCompatibility	OBJECT-TYPE
		SYNTAX	INTEGER { auto(1), enabled(2) }
		ACCESS	read-write
		STATUS	mandatory
		::= { wan 4 }



-- the lan group

lan		OBJECT IDENTIFIER ::= { bridge 7 }

lanNum	OBJECT-TYPE
		SYNTAX	Counter
		ACCESS	read-only
		STATUS	mandatory
		::= { lan 1 }

lanTbl	OBJECT-TYPE
		SYNTAX	SEQUENCE OF LanTblEnt
		ACCESS	not-accessible
		STATUS	mandatory
		::= { lan 2 }

lanTblEnt	OBJECT-TYPE
		SYNTAX	LanTblEnt
		ACCESS	not-accessible
		STATUS	mandatory
		::= { lanTbl 1 }

LanTblEnt	::= SEQUENCE {
			lanEntID
				INTEGER,
			lanEntShutdownThreshold
				INTEGER,
			lanEntFramingError
				Counter,
			lanEntLostPacketsError
				Counter,
			lanEntMemoryError
				Counter,
			lanEntOverflowError
				Counter,
			lanEntPacketInTooLongError
				Counter,
			lanEntCarrierLossError
				Counter,
			lanEntHeartbeatFailureError
				Counter,
			lanEntLateCollisionError
				Counter,
			lanEntPacketOutTooLongError
				Counter,
			lanEntRetryExceedError
				Counter
		}

lanEntID	OBJECT-TYPE
		SYNTAX	INTEGER
		ACCESS	read-only
		STATUS	mandatory
		::= { lanTblEnt 1 }

lanEntShutdownThreshold	OBJECT-TYPE
		SYNTAX	INTEGER
		ACCESS	read-only
		STATUS	mandatory
		::= { lanTblEnt 2 }

lanEntFramingError	OBJECT-TYPE
		SYNTAX	Counter
		ACCESS	read-only
		STATUS	mandatory
		::= { lanTblEnt 3 }

lanEntLostPacketsError	OBJECT-TYPE
		SYNTAX	Counter
		ACCESS	read-only
		STATUS	mandatory
		::= { lanTblEnt 4 }

lanEntMemoryError	OBJECT-TYPE
		SYNTAX	Counter
		ACCESS	read-only
		STATUS	mandatory
		::= { lanTblEnt 5 }

lanEntOverflowError	OBJECT-TYPE
		SYNTAX	Counter
		ACCESS	read-only
		STATUS	mandatory
		::= { lanTblEnt 6 }

lanEntPacketInTooLongError	OBJECT-TYPE
		SYNTAX	Counter
		ACCESS	read-only
		STATUS	mandatory
		::= { lanTblEnt 7 }

lanEntCarrierLossError	OBJECT-TYPE
		SYNTAX	Counter
		ACCESS	read-only
		STATUS	mandatory
		::= { lanTblEnt 8 }

lanEntHeartbeatFailureError	OBJECT-TYPE
		SYNTAX	Counter
		ACCESS	read-only
		STATUS	mandatory
		::= { lanTblEnt 9 }

lanEntLateCollisionError	OBJECT-TYPE
		SYNTAX	Counter
		ACCESS	read-only
		STATUS	mandatory
		::= { lanTblEnt 10 }

lanEntPacketOutTooLongError	OBJECT-TYPE
		SYNTAX	Counter
		ACCESS	read-only
		STATUS	mandatory
		::= { lanTblEnt 11 }

lanEntRetryExceedError	OBJECT-TYPE
		SYNTAX	Counter
		ACCESS	read-only
		STATUS	mandatory
		::= { lanTblEnt 12 }
END
