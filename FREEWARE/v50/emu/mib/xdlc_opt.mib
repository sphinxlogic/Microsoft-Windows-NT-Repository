-- Version 1.2.1.2, modified 3/15/94

	XDLC-OPT-MIB DEFINITIONS ::= BEGIN

	IMPORTS
		-- standard imports from SMI files

			mgmt, NetworkAddress, IpAddress, Counter, Gauge,
			TimeTicks
				FROM RFC1155-SMI
			OBJECT-TYPE
				FROM RFC-1212

		-- imports from cdx_6500.smi specific to this module. Should
		-- include Configuration, Statistics, and Control groups, as 
		-- applicable. The two imports listed below are *examples*.

			cdx6500Controls,
			cdx6500PCTPortProtocolGroup,
			cdx6500PSTPortProtocolGroup,
			Counter16
				FROM CDX6500-SMI;

	--	This MIB module uses the extended OBJECT-TYPE macro as
	--	defined in [14];


	-- textual conventions
		-- These are "aliases" for commonly-used variants of the four primitive
		-- object types provided by SNMP and also for user-defined object types.
		-- Any definitions provided here are good only in this MIB, unless
		-- explicitly listed as EXPORTs. DisplayString and PhysAddress are
		-- commonly used textual conventions.

	DisplayString ::=
		OCTET STRING
	-- This data type is used to model textual information taken
	-- from the NVT ASCII character set.	By convention, objects
	-- with this syntax are declared as having
	--
	--	 SIZE (0..255)

	PhysAddress ::=
		OCTET STRING
	-- This data type is used to model media addresses.	For many
	-- types of media, this will be in a binary representation.
	-- For example, an ethernet address would be represented as
	-- a string of 6 octets.




	-- The XDLC Port Configuration Table
	-- This table contains Configuration paramaters 
	-- for the XDLC Port table.
			
	cdx6500PPCTXDLCPortTable OBJECT-TYPE
		SYNTAX		SEQUENCE OF Cdx6500PPCTXDLCPortEntry
		ACCESS		not-accessible
		STATUS		mandatory
		DESCRIPTION
			"All of the configuration parameters relevant
			 to the XDLC port table."
		::= { cdx6500PCTPortProtocolGroup 13 }
			
	cdx6500PPCTXDLCPortEntry OBJECT-TYPE
		SYNTAX		Cdx6500XDLCPortEntry
		ACCESS		not-accessible
		STATUS		mandatory
		DESCRIPTION
			"A row of XDLC Port configuration parameters."
		INDEX	{ cdx6500xdlcpCfgPortNum }
		::= { cdx6500PPCTXDLCPortTable 1 }
			
	Cdx6500PPCTXDLCPortEntry ::=
		SEQUENCE {
			cdx6500xdlcpCfgPortNumber
				INTEGER,
			cdx6500xdlcpPortControl
				DisplayString,
			cdx6500xdlcpTXcoding
				INTEGER,
			cdx6500xdlcpLineType
				INTEGER,
			cdx6500xdlcpTxType
				INTEGER,
			cdx6500xdlcpClockSource
				INTEGER,
			cdx6500xdlcpClockSpeed
				INTEGER,
			cdx6500xdlcpStationCnt
				INTEGER,
			cdx6500xdlcpPollTimer
				INTERGER,
			cdx6500xdlcpPollPeriod
				INTEGER,
			cdx6500xdlcpTries
				INTEGER,
			cdx6500xdlcpPortOptions
				DisplayString,
			cdx6500xdlcpPortAddress
				DisplayString,
			cdx6500xdlcpRestartTimer
				INTEGER,
			cdx6500xdlcpResetTimer
				INTEGER,
			cdx6500xdlcpCallTimer
				INTEGER,
			cdx6500xdlcpClearTimer
				INTEGER
			}
			
	cdx6500xdlcpCfgPortNumber OBJECT-TYPE
		SYNTAX		INTEGER (1..54)
		ACCESS		read-only
		STATUS		mandatory
		DESCRIPTION
			"XDLC Port Number"
		DEFVAL { 1 }
		::= { cdx6500PPCTXDLCPortEntry 1 }
			
	cdx6500xdlcpPortControl OBJECT-TYPE
		SYNTAX		DisplayString (SIZE(2..4))
		ACCESS		read-only
		STATUS		mandatory
		DESCRIPTION
			"Specify any of the following port control options:

			  none  - no option specified
			  mb    - raise Pin 22 when the port becomes disabled"
		DEFVAL { none }
		::= { cdx6500PPCTXDLCPortEntry 2 }
			
	cdx6500xdlcpTxCoding OBJECT-TYPE
		SYNTAX		INTEGER	{
					nrz(0),
					nrzi(1)
					}
		ACCESS		read-only
		STATUS		mandatory
		DESCRIPTION
			"This is the data encoding used on the XDLC link.

			  nrz  - Non Return to Zero
			  nrzi - Non Return to Zero Inverted"
		DEFVAL { nrz }
		::= { cdx6500PPCTXDLCPortEntry 3 }
			
	cdx6500xdlcpLineType OBJECT-TYPE
		SYNTAX		INTEGER	{
					fdx(1)
					}
		ACCESS		read-only
		STATUS		mandatory
		DESCRIPTION
			"Type of line, indicates whether half duplex or full duplex
			signals are being generated.  FDX indicates communications occuring
			in both directions simultaneously between devices. Only Full Duplex
			operation is currently supported."
		DEFVAL { fdx }
		::= { cdx6500PPCTXDLCPortEntry 4 }
			
	cdx6500xdlcpTxType OBJECT-TYPE
		SYNTAX		INTEGER	{
					tws(0),
					twa(1)
					}
		ACCESS		read-only
		STATUS		mandatory
		DESCRIPTION
			"This is the transmission mode used on the line.

			  twa - Two Way Alternate used by most controllers.
			  tws - Two Way Simultaneous."
		DEFVAL { tws }
		::= { cdx6500PPCTXDLCPortEntry 5 }
			
	cdx6500xdlcpClockSource OBJECT-TYPE
		SYNTAX		INTEGER {
					int(0),
					ext(1)
					}
		ACCESS		read-only
		STATUS		mandatory
		DESCRIPTION
			"INT - Internal clock source.
			EXT - External clock source."
		DEFVAL { EXT }
		::= { cdx6500PPCTXDLCPortEntry 6 }
			
	cdx6500xdlcpClockSpeed OBJECT-TYPE
		SYNTAX		INTEGER (1200..80000)
		ACCESS		read-only
		STATUS		mandatory
		DESCRIPTION
			"This is the speed of the port in bits per second, when using
			internal clocking."
		DEFVAL { 9600 }
		::= { cdx6500PPCTXDLCPortEntry 7 }
			
	cdx6500xdlcpStationCnt OBJECT-TYPE
		SYNTAX		INTEGER (1..32)
		ACCESS		read-only
		STATUS		mandatory
		DESCRIPTION
			"This is the number of stations on the XDLC line."
		DEFVAL { 4 }
		::= { cdx6500PPCTXDLCPortEntry 8 }
			
	cdx6500xdlcpPollTimer OBJECT-TYPE
		SYNTAX		INTEGER (1..255)
		ACCESS		read-only
		STATUS		mandatory
		DESCRIPTION
			"Worst case delay for a slave to respond to a poll frame sent by
			the master, including modem turn around time, etc.
			Value in 10ths of second ( 30 = 3.0 seconds )."
		DEFVAL { 30 }
		::= { cdx6500PPCTXDLCPortEntry 9 }
			
	cdx6500xdlcpPollPeriod OBJECT-TYPE
		SYNTAX		INTEGER (50..250)
		ACCESS		read-only
		STATUS		mandatory
		DESCRIPTION
			"Time in milliseconds between polls when no data is exchanged."
		DEFVAL { 50 }
		::= { cdx6500PPCTXDLCPortEntry 10 }
			
	cdx6500xdlcpTries OBJECT-TYPE
		SYNTAX		INTEGER (1..16)
		ACCESS		read-only
		STATUS		mandatory
		DESCRIPTION
			"Maximum number of attempts to complete a transmission."
		DEFVAL { 10 }
		::= { cdx6500PPCTXDLCPortEntry 11 }
			
	cdx6500xdlcpPortOptions OBJECT-TYPE
		SYNTAX		DisplayString (SIZE(0..4))
		ACCESS		read-only
		STATUS		mandatory
		DESCRIPTION
			"Select options on this XDLC port as follows:

			  none - no option specified"
		DEFVAL { none }
		::= { cdx6500PPCTXDLCPortEntry 12 }
			
	cdx6500xdlcpPortAddress OBJECT-TYPE
		SYNTAX		DisplayString (SIZE(0..15))
		ACCESS		read-only
		STATUS		mandatory
		DESCRIPTION
			"When an XDLC port makes a call, this address is inserted into
			the calling address field."
		DEFVAL { '20'H } -- blank
		::= { cdx6500PPCTXDLCPortEntry 13 }
			
	cdx6500xdlcpRestartTimer OBJECT-TYPE
		SYNTAX		INTEGER (5..255)
		ACCESS		read-only
		STATUS		mandatory
		DESCRIPTION
			"Restart-Request timeout timer in seconds. If timer expires, request
			is sent again."
		DEFVAL { 180 }
		::= { cdx6500PPCTXDLCPortEntry 14 }
			
	cdx6500xdlcpResetTimer OBJECT-TYPE
		SYNTAX		INTEGER (5..255)
		ACCESS		read-only
		STATUS		mandatory
		DESCRIPTION
			"Reset-Request timeout timer in seconds. If timer expires, request
			is sent again."
		DEFVAL { 180 }
		::= { cdx6500PPCTXDLCPortEntry 15 }
			
	cdx6500xdlcpCallTimer OBJECT-TYPE
		SYNTAX		INTEGER (5..255)
		ACCESS		read-only
		STATUS		mandatory
		DESCRIPTION
			"Call-Request timeout timer in seconds. If timer expires, call is
			cleared."
		DEFVAL { 200 }
		::= { cdx6500PPCTXDLCPortEntry 16 }
			
	cdx6500xdlcpClearTimer OBJECT-TYPE
		SYNTAX		INTEGER (5..255)
		ACCESS		read-only
		STATUS		mandatory
		DESCRIPTION
			"Clear-Request timeout timer in seconds. If timer expires, request
			is sent again."
		DEFVAL { 180 }
		::= { cdx6500PPCTXDLCPortEntry 17 }




	-- The XDLC Port Statistics Table
	-- This table contains Statistics paramaters 
	-- for the XDLC Port table.
			
	cdx6500PPSTXDLCPortTable OBJECT-TYPE
		SYNTAX		SEQUENCE OF Cdx6500PPSTXDLCPortEntry
		ACCESS		not-accessible
		STATUS		mandatory
		DESCRIPTION
			"All of the statistics parameters relevant
			 to the XDLC Port table."
		::= { cdx6500PSTPortProtocolGroup 13 }
				
	cdx6500PPSTXDLCPortEntry OBJECT-TYPE
		SYNTAX		Cdx6500PPSTXDLCPortEntry
		ACCESS		not-accessible
		STATUS		mandatory
		DESCRIPTION
			"A row of XDLC Port statistics parameters."
		INDEX	{ cdx6500xdlcpStatsPortNum }
		::= { cdx6500PPSTXDLCPortTable 1 }
			
	Cdx6500PPSTXDLCPortEntry ::=
		SEQUENCE {
			cdx6500xdlcpStatsPortNumber
				INTEGER,
			cdx6500xdlcpPortStatus
				INTEGER,
			cdx6500xdlcpPortSpeed
				INTEGER,
			cdx6500xdlcpUtilizationIn
				INTEGER,
			cdx6500xdlcpUtilizationOut
				INTEGER,
			cdx6500xdlcpCharInTotal
				Counter,
			cdx6500xdlcpCharOutTotal
				Counter,
			cdx6500xdlcpCharsInPerSec
				INTEGER,
			cdx6500xdlcpCharsOutPerSec
				INTEGER,
			cdx6500xdlcpFrameInTotal
				Counter,
			cdx6500xdlcpFrameOutTotal
				Counter,
			cdx6500xdlcpFramesInPerSec
				INTEGER,
			cdx6500xdlcpFramesOutPerSec
				INTEGER,
			cdx6500xdlcpCRCErrors
				Counter16,
			cdx6500xdlcpOverrunErrors
				Counter16,
			cdx6500xdlcpUnderrunErrors
				Counter16,
			cdx6500xdlcpRNRFramesIn
				Counter,
			cdx6500xdlcpRNRFramesOut
				Counter,
			cdx6500xdlcpRRFramesIn
				Counter,
			cdx6500xdlcpRRFramesOut
				Counter,
			cdx6500xdlcpREJFramesIn
				Counter,
			cdx6500xdlcpREJFramesOut
				Counter,
			cdx6500xdlcpMX25StationsUp
				INTEGER,
			cdx6500xdlcpMX25StationsDown
				INTEGER,
			cdx6500xdlcpMX25StationsDisabled
				INTEGER,
			cdx6500xdlcpSDLCStationsUp
				INTEGER,
			cdx6500xdlcpSDLCStationsDown
				INTEGER,
			cdx6500xdlcpSDLCStationsDisabled
				INTEGER,
			cdx6500xdlcpStateChange
				DisplayString,
			cdx6500xdlcpLinkDowns
				Counter16,
			cdx6500xdlcpPacketsQueued
				INTEGER,
			cdx6500xdlcpSNRMInFrames
				Counter,
			cdx6500xdlcpSNRMOutFrames
				Counter,
			cdx6500xdlcpUAInFrames
				Counter,
			cdx6500xdlcpUAOutFrames
				Counter,
			cdx6500xdlcpDMInFrames
				Counter,
			cdx6500xdlcpDMOutFrames
				Counter,
			cdx6500xdlcpXIDInFrames
				Counter,
			cdx6500xdlcpXIDOutFrames
				Counter,
			cdx6500xdlcpDISCInFrames
				Counter,
			cdx6500xdlcpDISCOutFrames
				Counter,
			cdx6500xdlcpRDInFrames
				Counter,
			cdx6500xdlcpRDOutFrames
				Counter,
			cdx6500xdlcpFRMRInFrames
				Counter,
			cdx6500xdlcpFRMROutFrames
				Counter,
			cdx6500xdlcpUPInFrames
				Counter,
			cdx6500xdlcpUPOutFrames
				Counter,
			cdx6500xdlcpTESTInFrames
				Counter,
			cdx6500xdlcpTESTOutFrames
				Counter
			}
			
	cdx6500xdlcpStatsPortNumber OBJECT-TYPE
		SYNTAX		INTEGER (1..54)
		ACCESS		read-only
		STATUS		mandatory
		DESCRIPTION
			"Specifies a specifiec port (physical port number) in the node."
		::= { cdx6500PPSTXDLCPortEntry 1 }
			
	cdx6500xdlcpPortStatus OBJECT-TYPE
		SYNTAX		INTEGER {
					disabled(0),
					enabled(1),
					busyOut(2),
					up(3),
					down(4)
					}
		ACCESS		read-only
		STATUS		mandatory
		DESCRIPTION
			"Specifies the current port status.

			up: At least one station is responding to polls.
			down: None of the stations are responding to polls.
			disabled: The port is disabled by user."
		::= { cdx6500PPSTXDLCPortEntry 2 }
			
	cdx6500xdlcpPortSpeed OBJECT-TYPE
		SYNTAX		INTEGER
		ACCESS		read-only
		STATUS		mandatory
		DESCRIPTION
			"The measured port speed in bits per second."
		::= { cdx6500PPSTXDLCPortEntry 3 }
			
	cdx6500xdlcpUtilizationIn OBJECT-TYPE
		SYNTAX		INTEGER (0..100)
		ACCESS		read-only
		STATUS		mandatory
		DESCRIPTION
			"Indicates a percentage of the port recources that are currently
			in use from the line to the port."
		::= { cdx6500PPSTXDLCPortEntry 4 }
			
	cdx6500xdlcpUtilizationOut OBJECT-TYPE
		SYNTAX		INTEGER (0..100)
		ACCESS		read-only
		STATUS		mandatory
		DESCRIPTION
			"Indicates a percentage of the port recources that are currently
			in use from the port to the line."
		::= { cdx6500PPSTXDLCPortEntry 5 }
			
	cdx6500xdlcpCharInTotal OBJECT-TYPE
		SYNTAX		Counter
		ACCESS		read-only
		STATUS		mandatory
		DESCRIPTION
			"Total number of characters processed until now, not including
			header characters."
		::= { cdx6500PPSTXDLCPortEntry 6 }
			
	cdx6500xdlcpCharOutTotal OBJECT-TYPE
		SYNTAX		Counter
		ACCESS		read-only
		STATUS		mandatory
		DESCRIPTION
			"Total number of characters processed until now, not including
			header characters."
		::= { cdx6500PPSTXDLCPortEntry 7 }
			
	cdx6500xdlcpCharsInPerSec OBJECT-TYPE
		SYNTAX		INTEGER
		ACCESS		read-only
		STATUS		mandatory
		DESCRIPTION
			"The average number of characters received per second."
		::= { cdx6500PPSTXDLCPortEntry 8 }
			
	cdx6500xdlcpCharsOutPerSec OBJECT-TYPE
		SYNTAX		INTEGER
		ACCESS		read-only
		STATUS		mandatory
		DESCRIPTION
			"The average number of characters transmitted per second."
		::= { cdx6500PPSTXDLCPortEntry 9 }
			
	cdx6500xdlcpFrameInTotal OBJECT-TYPE
		SYNTAX		Counter
		ACCESS		read-only
		STATUS		mandatory
		DESCRIPTION
			"Total number of MX25 and SDLC frames processed until now."
		::= { cdx6500PPSTXDLCPortEntry 10 }
			
	cdx6500xdlcpFrameOutTotal OBJECT-TYPE
		SYNTAX		Counter
		ACCESS		read-only
		STATUS		mandatory
		DESCRIPTION
			"Total number of MX25 and SDLC frames processed until now."
	::= { cdx6500PPSTXDLCPortEntry 11 }
			
	cdx6500xdlcpFramesInPerSec OBJECT-TYPE
		SYNTAX		INTEGER
		ACCESS		read-only
		STATUS		mandatory
		DESCRIPTION
			"The average number of frames received per second."
		::= { cdx6500PPSTXDLCPortEntry 12 }
			
	cdx6500xdlcpFramesOutPerSec OBJECT-TYPE
		SYNTAX		INTEGER
		ACCESS		read-only
		STATUS		mandatory
		DESCRIPTION
			"The average number of frames transmitted per second."
		::= { cdx6500PPSTXDLCPortEntry 13 }
			
	cdx6500xdlcpCRCErrors OBJECT-TYPE
		SYNTAX		Counter16
		ACCESS		read-only
		STATUS		mandatory
		DESCRIPTION
			"Total number of CRC errors counted by the I/O driver."
		::= { cdx6500PPSTXDLCPortEntry 14 }
			
	cdx6500xdlcpOverrunErrors OBJECT-TYPE
		SYNTAX		Counter16
		ACCESS		read-only
		STATUS		mandatory
		DESCRIPTION
			"Total number of overrun errors counted by the I/O driver."
		::= { cdx6500PPSTXDLCPortEntry 15 }
			
	cdx6500xdlcpUnderrunErrors OBJECT-TYPE
		SYNTAX		Counter16
		ACCESS		read-only
		STATUS		mandatory
		DESCRIPTION
			"Total number of overrun errors counted by the I/O driver."
		::= { cdx6500PPSTXDLCPortEntry 16 }
			
	cdx6500xdlcpRNRFramesIn OBJECT-TYPE
		SYNTAX		Counter
		ACCESS		read-only
		STATUS		mandatory
		DESCRIPTION
			"Indicates the total number of RNR frames received."
		::= { cdx6500PPSTXDLCPortEntry 17 }
			
	cdx6500xdlcpRNRFramesOut OBJECT-TYPE
		SYNTAX		Counter
		ACCESS		read-only
		STATUS		mandatory
		DESCRIPTION
			"Indicates the total number of RNR frames transmitted."
		::= { cdx6500PPSTXDLCPortEntry 18 }
			
	cdx6500xdlcpRRFramesIn OBJECT-TYPE
		SYNTAX		Counter
		ACCESS		read-only
		STATUS		mandatory
		DESCRIPTION
			"Indicates the total number of RR frames received."
		::= { cdx6500PPSTXDLCPortEntry 19 }
			
	cdx6500xdlcpRRFramesOut OBJECT-TYPE
		SYNTAX		Counter
		ACCESS		read-only
		STATUS		mandatory
		DESCRIPTION
			"Indicates the total number of RR frames transmitted."
		::= { cdx6500PPSTXDLCPortEntry 20 }
			
	cdx6500xdlcpREJFramesIn OBJECT-TYPE
		SYNTAX		Counter
		ACCESS		read-only
		STATUS		mandatory
		DESCRIPTION
			"Indicates the total number of REJ frames received."
		::= { cdx6500PPSTXDLCPortEntry 21 }
			
	cdx6500xdlcpREJFramesOut OBJECT-TYPE
		SYNTAX		Counter
		ACCESS		read-only
		STATUS		mandatory
		DESCRIPTION
			"Indicates the total number of REJ frames transmitted."
		::= { cdx6500PPSTXDLCPortEntry 22 }
			
	cdx6500xdlcpMX25StationsUp OBJECT-TYPE
		SYNTAX		INTEGER
		ACCESS		read-only
		STATUS		mandatory
		DESCRIPTION
			"Number of MX.25 stations up."
		::= { cdx6500PPSTXDLCPortEntry 23 }
			
	cdx6500xdlcpMX25StationsDown OBJECT-TYPE
		SYNTAX		INTEGER
		ACCESS		read-only
		STATUS		mandatory
		DESCRIPTION
			"Number of MX.25 stations down."
		::= { cdx6500PPSTXDLCPortEntry 24 }
			
	cdx6500xdlcpMX25StationsDisabled OBJECT-TYPE
		SYNTAX		INTEGER
		ACCESS		read-only
		STATUS		mandatory
		DESCRIPTION
			"Number of MX.25 stations disabled."
		::= { cdx6500PPSTXDLCPortEntry 25 }
			
	cdx6500xdlcpSDLCStationsUp OBJECT-TYPE
		SYNTAX		INTEGER
		ACCESS		read-only
		STATUS		mandatory
		DESCRIPTION
			"Number of SDLC stations up."
		::= { cdx6500PPSTXDLCPortEntry 26 }
			
	cdx6500xdlcpSDLCStationsDown OBJECT-TYPE
		SYNTAX		INTEGER
		ACCESS		read-only
		STATUS		mandatory
		DESCRIPTION
			"Number of SDLC stations down."
		::= { cdx6500PPSTXDLCPortEntry 27 }
			
	cdx6500xdlcpSDLCStationsDisabled OBJECT-TYPE
		SYNTAX		INTEGER
		ACCESS		read-only
		STATUS		mandatory
		DESCRIPTION
			"Number of SDLC stations disabled."
		::= { cdx6500PPSTXDLCPortEntry 28 }

	cdx6500xdlcpStateChange OBJECT-TYPE
		SYNTAX		DisplayString (SIZE(0..20))
		ACCESS		read-only
		STATUS		mandatory
		DESCRIPTION
			"The date and time when the link entered the current state."
		::= { cdx6500PPSTXDLCPortEntry 29 }
			
	cdx6500xdlcpLinkDowns OBJECT-TYPE
		SYNTAX		Counter16
		ACCESS		read-only
		STATUS		mandatory
		DESCRIPTION
			"Total number of times link has made a transition from the UP state
			to the DOWN state."
		::= { cdx6500PPSTXDLCPortEntry 30 }

	cdx6500xdlcpPacketsQueued OBJECT-TYPE
		SYNTAX		INTEGER
		ACCESS		read-only
		STATUS		mandatory
		DESCRIPTION
			"Total number of packets queued at the XDLC protocol layer by the
			transmitter."
		::= { cdx6500PPSTXDLCPortEntry 31 }


	cdx6500xdlcpSNRMInFrames OBJECT-TYPE
		SYNTAX		Counter
		ACCESS		read-only
		STATUS		mandatory
		DESCRIPTION
			"Total number of SNRM frames received until the present time."
		::= { cdx6500PPSTXDLCPortEntry 32 }


	cdx6500xdlcpSNRMOutFrames OBJECT-TYPE
		SYNTAX		Counter
		ACCESS		read-only
		STATUS		mandatory
		DESCRIPTION
			"Total number of SNRM frames transmitted until the present time."
		::= { cdx6500PPSTXDLCPortEntry 33 }


	cdx6500xdlcpUAInFrames OBJECT-TYPE
		SYNTAX		Counter
		ACCESS		read-only
		STATUS		mandatory
		DESCRIPTION
			"Total number of UA frames received until the present time."
		::= { cdx6500PPSTXDLCPortEntry 34 }


	cdx6500xdlcpUAOutFrames OBJECT-TYPE
		SYNTAX		Counter
		ACCESS		read-only
		STATUS		mandatory
		DESCRIPTION
			"Total number of UA frames transmitted until the present time."
		::= { cdx6500PPSTXDLCPortEntry 35 }


	cdx6500xdlcpDMInFrames OBJECT-TYPE
		SYNTAX		Counter
		ACCESS		read-only
		STATUS		mandatory
		DESCRIPTION
			"Total number of DM frames received until the present time."
		::= { cdx6500PPSTXDLCPortEntry 36 }


	cdx6500xdlcpDMOutFrames OBJECT-TYPE
		SYNTAX		Counter
		ACCESS		read-only
		STATUS		mandatory
		DESCRIPTION
			"Total number of DM frames transmitted until the present time."
		::= { cdx6500PPSTXDLCPortEntry 37 }


	cdx6500xdlcpXIDInFrames OBJECT-TYPE
		SYNTAX		Counter
		ACCESS		read-only
		STATUS		mandatory
		DESCRIPTION
			"Total number of XID frames received until the present time."
		::= { cdx6500PPSTXDLCPortEntry 38 }


	cdx6500xdlcpXIDOutFrames OBJECT-TYPE
		SYNTAX		Counter
		ACCESS		read-only
		STATUS		mandatory
		DESCRIPTION
			"Total number of XID frames transmitted until the present time."
		::= { cdx6500PPSTXDLCPortEntry 39 }


	cdx6500xdlcpDISCInFrames OBJECT-TYPE
		SYNTAX		Counter
		ACCESS		read-only
		STATUS		mandatory
		DESCRIPTION
			"Total number of DISC frames received until the present time."
		::= { cdx6500PPSTXDLCPortEntry 40 }


	cdx6500xdlcpDISCOutFrames OBJECT-TYPE
		SYNTAX		Counter
		ACCESS		read-only
		STATUS		mandatory
		DESCRIPTION
			"Total number of DISC frames transmitted until the present time."
		::= { cdx6500PPSTXDLCPortEntry 41 }


	cdx6500xdlcpRDInFrames OBJECT-TYPE
		SYNTAX		Counter
		ACCESS		read-only
		STATUS		mandatory
		DESCRIPTION
			"Total number of RD frames received until the present time."
		::= { cdx6500PPSTXDLCPortEntry 42 }


	cdx6500xdlcpRDOutFrames OBJECT-TYPE
		SYNTAX		Counter
		ACCESS		read-only
		STATUS		mandatory
		DESCRIPTION
			"Total number of RD frames transmitted until the present time."
		::= { cdx6500PPSTXDLCPortEntry 43 }


	cdx6500xdlcpFRMRInFrames OBJECT-TYPE
		SYNTAX		Counter
		ACCESS		read-only
		STATUS		mandatory
		DESCRIPTION
			"Total number of FRMR frames received until the present time."
		::= { cdx6500PPSTXDLCPortEntry 44 }


	cdx6500xdlcpFRMROutFrames OBJECT-TYPE
		SYNTAX		Counter
		ACCESS		read-only
		STATUS		mandatory
		DESCRIPTION
			"Total number of FRMR frames transmitted until the present time."
		::= { cdx6500PPSTXDLCPortEntry 45 }


	cdx6500xdlcpUPInFrames OBJECT-TYPE
		SYNTAX		Counter
		ACCESS		read-only
		STATUS		mandatory
		DESCRIPTION
			"Total number of UP frames received until the present time."
		::= { cdx6500PPSTXDLCPortEntry 46 }


	cdx6500xdlcpUPOutFrames OBJECT-TYPE
		SYNTAX		Counter
		ACCESS		read-only
		STATUS		mandatory
		DESCRIPTION
			"Total number of UP frames transmitted until the present time."
		::= { cdx6500PPSTXDLCPortEntry 47 }


	cdx6500xdlcpTESTInFrames OBJECT-TYPE
		SYNTAX		Counter
		ACCESS		read-only
		STATUS		mandatory
		DESCRIPTION
			"Total number of TEST frames received until the present time."
		::= { cdx6500PPSTXDLCPortEntry 48 }


	cdx6500xdlcpTESTOutFrames OBJECT-TYPE
		SYNTAX		Counter
		ACCESS		read-only
		STATUS		mandatory
		DESCRIPTION
			"Total number of TEST frames transmitted until the present time."
		::= { cdx6500PPSTXDLCPortEntry 49 }



	-- The XDLC Station Configuration Tables
	-- These tables contain Configuration paramaters 
	-- for the XDLC Station table.
			
	cdx6500SPCTXDLCStationTable OBJECT IDENTIFIER ::= { cdx6500PCTStationProtocolGroup 5 }




	-- The XDLC Station Configuration Tables
	-- These tables contain Configuration paramaters 
	-- for the XDLC Station table, used for both
	-- SDLC and MX25 stations.
			
	cdx6500SPCTXDLCStnTable OBJECT-TYPE
		SYNTAX		SEQUENCE OF Cdx6500SPCTXDLCStnEntry
		ACCESS		not-accessible
		STATUS		mandatory
		DESCRIPTION
			"All of the configuration parameters relevant
			 to the XDLC station table."
		::= { cdx6500SPCTXDLCStationTable 1 }
			
	cdx6500SPCTXDLCStnEntry OBJECT-TYPE
		SYNTAX		Cdx6500SPCTXDLCStnEntry
		ACCESS		not-accessible
		STATUS		mandatory
		DESCRIPTION
			"A row of XDLC station configuration parameters."
		INDEX	{ cdx6500xdlcsCfgPortNum, cdx6500xdlcsCfgStationNum }
		::= { cdx6500SPCTXDLCStnTable 1 }
			
	Cdx6500SPCTXDLCStnEntry ::=
		SEQUENCE {
			cdx6500xdlcsCfgPortNumber
				INTEGER,
			cdx6500xdlcsCfgStationNumber
				INTEGER,
			cdx6500xdlcsStationType
				INTEGER
			}
	cdx6500xdlcsCfgPortNumber OBJECT-TYPE
		SYNTAX		INTEGER (1..54)
		ACCESS		read-only
		STATUS		mandatory
		DESCRIPTION
			"XDLC Port Number"
		DEFVAL { 1 }
		::= { cdx6500SPCTXDLCStnEntry 1 }
			
	cdx6500xdlcsCfgStationNumber OBJECT-TYPE
		SYNTAX		INTEGER (1..32)
		ACCESS		read-only
		STATUS		mandatory
		DESCRIPTION
			"The number of the station on the multidrop line.  Also used for
			routing purposes."
		DEFVAL { 1 }
		::= { cdx6500SPCTXDLCStnEntry 2 }
			
	cdx6500xdlcsStationType OBJECT-TYPE
		SYNTAX		INTEGER {
					sdlc(0),
					mx25(1)
					}
		ACCESS		read-only
		STATUS		mandatory
		DESCRIPTION
			"Enter the type of station to configure.

			  sdlc - SDLC Station.
			  mx25 - MX25 Station."
		DEFVAL { mx25 }
		::= { cdx6500SPCTXDLCStnEntry 3 }





	-- The XDLC SDLC Station Configuration Table
	-- This table contains Configuration paramaters 
	-- for the XDLC Station table, specific to SDLC stations.
		
	cdx6500SPCTXDLCSDLCStnTable OBJECT-TYPE
		SYNTAX		SEQUENCE OF Cdx6500SPCTXDLCSDLCStnEntry
		ACCESS		not-accessible
		STATUS		mandatory
		DESCRIPTION
			"All of the configuration parameters relevant
			 to the XDLC SDLC station table."
		::= { cdx6500SPCTXDLCStationTable 2 }
			
	cdx6500SPCTXDLCSDLCStnEntry OBJECT-TYPE
		SYNTAX		Cdx6500SPCTXDLCSDLCStnEntry
		ACCESS		not-accessible
		STATUS		mandatory
		DESCRIPTION
			"A row of XDLC SDLC station configuration parameters."
		INDEX	{ cdx6500xdlcssdlcCfgPortNum, cdx6500xdlcssdlcCfgStationNum }
		::= { cdx6500SPCTXDLCSDLCStnTable 1 }
			
	Cdx6500SPCTXDLCSDLCStnEntry ::=
		SEQUENCE {
			cdx6500xdlcsdlcCfgPortNum
				INTEGER,
			cdx6500xdlcsdlcCfgStationNum
				INTEGER,
			cdx6500xdlcsdlcStationAddress
				DisplayString,
			cdx6500xdlcsdlcFrameWinSize
				INTEGER,
			cdx6500xdlcsdlcAutocallMnem
				DisplayString,
			cdx6500xdlcsdlcprotocolID
				DisplayString,
			cdx6500xdlcsdlcCUG
				DisplayString,
			cdx6500xdlcsdlcOptions
				DisplayString,
			cdx6500xdlcsdlcXID
				DisplayString,
			cdx6500xdlcsdlcStnSubaddress
				DisplayString,
			cdx6500xdlcsdlcBillingRecords
				INTEGER
			}
			
	cdx6500xdlcsdlcCfgPortNum OBJECT-TYPE
		SYNTAX		INTEGER (1..54)
		ACCESS		read-only
		STATUS		mandatory
		DESCRIPTION
			"XDLC Port Number"
		DEFVAL { 1 }
		::= { cdx6500SPCTXDLCSDLCStnEntry 1 }
			
	cdx6500xdlcsdlcCfgStationNum OBJECT-TYPE
		SYNTAX		INTEGER (1..32)
		ACCESS		read-only
		STATUS		mandatory
		DESCRIPTION
			"The number of the station on the multidrop line.  Also used for
			routing purposes."
		DEFVAL { 1 }
		::= { cdx6500SPCTXDLCSDLCStnEntry 2 }
			
	cdx6500xdlcsdlcStationAddress OBJECT-TYPE
		SYNTAX		DisplayString (SIZE(0..2))
		ACCESS		read-only
		STATUS		mandatory
		DESCRIPTION
			"The station address on the multidrop line."
		DEFVAL { 01 }
		::= { cdx6500SPCTXDLCSDLCStnEntry 3 }
			
	cdx6500xdlcsdlcFrameWinSize OBJECT-TYPE
		SYNTAX		INTEGER (1..7)
		ACCESS		read-only
		STATUS		mandatory
		DESCRIPTION
			"Frame level window size must be set to the same value in
			devices at each end of the link."
		DEFVAL { 7 }
		::= { cdx6500SPCTXDLCSDLCStnEntry 4 }
			
	cdx6500xdlcsdlcAutocallMnem OBJECT-TYPE
		SYNTAX		DisplayString (SIZE(0..8))
		ACCESS		read-only
		STATUS		mandatory
		DESCRIPTION
			"This mnemonic references the remote address which will be called
			when polling activity is detected on the sdlc line."
		DEFVAL { '20'H } -- blank
		::= { cdx6500SPCTXDLCSDLCStnEntry 5 }
			
	cdx6500xdlcsdlcProtocolID OBJECT-TYPE
		SYNTAX		DisplayString (SIZE(1..9))
		ACCESS		read-only
		STATUS		mandatory
		DESCRIPTION
			"The protocol identifier is the first four bytes of
			the call user data.  If not configured the PAD will use
			C3000000 as the protocol ID in the call."
		::= { cdx6500SPCTXDLCSDLCStnEntry 6 }
			
	cdx6500xdlcsdlcCUG OBJECT-TYPE
		SYNTAX		DisplayString (SIZE(0..23))
		ACCESS		read-only
		STATUS		mandatory
		DESCRIPTION
			"The station may be a member of up to 8 different Closed User
			Groups (CUGs). Each CUG membership must be a two digit number
			( except -- )and separated by a comma. ( e.g. 12,34,56,09,02,03 ).

			  --    - No CUG Membership
			  00-99 - CUG Membership"
		::= { cdx6500SPCTXDLCSDLCStnEntry 7 }
			
	cdx6500xdlcsdlcOptions OBJECT-TYPE
		SYNTAX		DisplayString (SIZE(3..24))
		ACCESS		read-only
		STATUS		mandatory
		DESCRIPTION
			"Select options on this SDLC station as follows:

			  none  - no option specified
			  cug   - check closed user group in incoming calls, and insert closed
			          user group facility in outgoing calls.
			  qrrs  - HPAD sends QRR after QLLC link comes up
			  xids  - TPAD responds to QXIDs with XID configured for this station
			          XIDs are not sent to the Cluster Controller.
			  xid3  - HPAD and TPAD will pass XIDs transparently, This option
				  should
			          not be set if XIDs option is selected. Corresponding
			          station options must be XID3.
			  discs - TPAD sends a DISC frame when station goes down.
			          The DISC may be retransmitted up to Tries times, if the
			          Cluster Controller does not respond, before sending a SNRM."
		DEFVAL { none }
		::= { cdx6500SPCTXDLCSDLCStnEntry 8 }
			
	cdx6500xdlcsdlcXID OBJECT-TYPE
		SYNTAX		DisplayString (SIZE(0..15))
		ACCESS		read-only
		STATUS		mandatory
		DESCRIPTION
			"With this option selected, the TPAD's response to a QXID will
			contain the XID identification value defined in this parameter
			instead of from an exchange of identifications with the cluster
			controller. XIDs are not sent to the cluster controller."
		DEFVAL { '20'H } -- blank
		::= { cdx6500SPCTXDLCSDLCStnEntry 9 }
			
	cdx6500xdlcsdlcStnSubaddress OBJECT-TYPE
		SYNTAX		DisplayString (SIZE(0..3))
		ACCESS		read-only
		STATUS		mandatory
		DESCRIPTION
			"The calling subaddress is appended to the port address
			to create the calling address in the autocall generated."
		DEFVAL { '20'H } -- blank
		::= { cdx6500SPCTXDLCSDLCStnEntry 10 }
			
	cdx6500xdlcsdlcBillingRecords OBJECT-TYPE
		SYNTAX		INTEGER	{
					off(0),
					on(1)
					}
		ACCESS		read-only
		STATUS		mandatory
		DESCRIPTION
			"This controls whether billing (accounting) records will be created for
			calls on this port."
		::= { cdx6500SPCTXDLCSDLCStnEntry 11 }




	-- The XDLC MX25 Station Configuration Table
	-- This table contains Configuration paramaters 
	-- for the XDLC Station table, specific to MX25 stations.
			
	cdx6500SPCTXDLCMX25StnTable OBJECT-TYPE
		SYNTAX		SEQUENCE OF Cdx6500SPCTXDLCMX25StnEntry
		ACCESS		not-accessible
		STATUS		mandatory
		DESCRIPTION
			"All of the configuration parameters relevant
			 to the XDLC MX.25 station table."
		::= { cdx6500SPCTXDLCStationTable 3 }
			
	cdx6500SPCTXDLCMX25StnEntry OBJECT-TYPE
		SYNTAX		Cdx6500SPCTXDLCMX25StnEntry
		ACCESS		not-accessible
		STATUS		mandatory
		DESCRIPTION
			"A row of XDLC MX.25 station configuration parameters."
		INDEX	{ cdx6500mx25sCfgPortNum, cdx6500mx25sCfgStationNum }
		::= { cdx6500SPCTXDLCMX25StnTable 1 }
			
	Cdx6500SPCTXDLCMX25StnEntry ::=
		SEQUENCE {
			cdx6500xdlcmx25CfgPortNum
				INTEGER,
			cdx6500xdlcmx25CfgStationNum
				INTEGER,
			cdx6500xdlcmx25StationAddress
				DisplayString,
			cdx6500xdlcmx25PVCChannels
				INTEGER,
			cdx6500xdlcmx25StartingPVC
				INTEGER,
			cdx6500xdlcmx25SVCChannels
				INTEGER,
			cdx6500xdlcmx25StartingSVC
				INTEGER,
			cdx6500xdlcmx25FrameWinSize
				INTEGER,
			cdx6500xdlcmx25PacketWinSize
				INTEGER,
			cdx6500xdlcmx25Options
				DisplayString,
			cdx6500xdlcmx25RCDestination
				DisplayString,
			cdx6500xdlcmx25CUG
				DisplayString,
			cdx6500xdlcmx25BillingRecords
				INTEGER,
			cdx6500xdlcmx25UpperQueue
				INTEGER,
			cdx6500xdlcmx25LowerQueue
				INTEGER
			}
			
	cdx6500xdlcmx25CfgPortNum OBJECT-TYPE
		SYNTAX		INTEGER (1..54)
		ACCESS		read-only
		STATUS		mandatory
		DESCRIPTION
			"XDLC Port Number"
		DEFVAL { 1 }
		::= { cdx6500SPCTXDLCMX25StnEntry 1 }
			
	cdx6500xdlcmx25CfgStationNum OBJECT-TYPE
		SYNTAX		INTEGER (1..32)
		ACCESS		read-only
		STATUS		mandatory
		DESCRIPTION
			"The number of the station on the multidrop line.  Also used for
			routing purposes."
		DEFVAL { 1 }
		::= { cdx6500SPCTXDLCMX25StnEntry 2 }
			
	cdx6500xdlcmx25StationAddress OBJECT-TYPE
		SYNTAX		DisplayString (SIZE(0..2))
		ACCESS		read-only
		STATUS		mandatory
		DESCRIPTION
			"The station address on the multidrop line."
		DEFVAL { 04 }
		::= { cdx6500SPCTXDLCMX25StnEntry 3 }
			
	cdx6500xdlcmx25PVCChannels OBJECT-TYPE
		SYNTAX		INTEGER (0..128)
		ACCESS		read-only
		STATUS		mandatory
		DESCRIPTION
			"Number of logical channels used for Permanent Virtual Circuits.
			The total number of PVC and SVC channels on a link should be kept as
			small as possible and consistent with needs.
			PVC connections must be configured in the PVC Table."
		DEFVAL { 0 }
		::= { cdx6500SPCTXDLCMX25StnEntry 4 }
			
	cdx6500xdlcmx25StartingPVC OBJECT-TYPE
		SYNTAX		INTEGER (1..255)
		ACCESS		read-only
		STATUS		mandatory
		DESCRIPTION
			"This is the starting logical channel number for the Permanent Virtual
			Circuits on this link. Not used if the number of PVCs = 0."
		DEFVAL { 1 }
		::= { cdx6500SPCTXDLCMX25StnEntry 5 }
			
	cdx6500xdlcmx25SVCChannels OBJECT-TYPE
		SYNTAX		INTEGER (0..255)
		ACCESS		read-only
		STATUS		mandatory
		DESCRIPTION
			"Number of logical channels used in Switched Virtual Circuits.
			The total number of PVC and SVC channels on a link should be kept as
			small as possible and consistent with needs."
		DEFVAL { 16 }
		::= { cdx6500SPCTXDLCMX25StnEntry 6 }
			
	cdx6500xdlcmx25StartingSVC OBJECT-TYPE
		SYNTAX		INTEGER (0..255)
		ACCESS		read-only
		STATUS		mandatory
		DESCRIPTION
			"This is the starting logical channel number for the Switched Virtual
			Circuits on this link. Not used if the number of SVCs = 0."
		DEFVAL { 1 }
		::= { cdx6500SPCTXDLCMX25StnEntry 7 }
			
	cdx6500xdlcmx25FrameWinSize OBJECT-TYPE
		SYNTAX		INTEGER (1..7)
		ACCESS		read-only
		STATUS		mandatory
		DESCRIPTION
			"Frame level window size must be set to the same value in
			devices at each end of the link."
		DEFVAL { 7 }
		::= { cdx6500SPCTXDLCMX25StnEntry 8 }
			
	cdx6500xdlcmx25PacketWinSize OBJECT-TYPE
		SYNTAX		INTEGER (1..7)
		ACCESS		read-only
		STATUS		mandatory
		DESCRIPTION
			"Packet level window size must be set to the same value in
			devices at each end of the link."
		DEFVAL { 2 }
		::= { cdx6500SPCTXDLCMX25StnEntry 9 }
			
	cdx6500xdlcmx25Options OBJECT-TYPE
		SYNTAX		DisplayString (SIZE(0..17))
		ACCESS		read-only
		STATUS		mandatory
		DESCRIPTION
			"Select options on this MX.25 port as follows:

			  none - no option specified
			  hold - hold calls over link restart
			  cug  - check closed user group; otherwise, CUG passes transparently
			  inl  - inter-node link. Link goes to another 6500 device
			  delay - enable delay path trace on this link (link must be connected
				  to Rel. 4.xx node)

			Any combination of the above specified by summing
			(e.g. HOLD+CUG+. . .)."
		::= { cdx6500SPCTXDLCMX25StnEntry 10 }
			
	cdx6500xdlcmx25RCDestination OBJECT-TYPE
		SYNTAX		DisplayString (SIZE(0..32))
		ACCESS		read-only
		STATUS		mandatory
		DESCRIPTION
			"All calls entering this port will be routed to the destination
			specified in this parameter, irrespective of route selection table
			entries. For example, to route calls to port 1, use P1.
			To route calls to port 2, station 4, use P2S4.
			Blank this field to disable this function."
		DEFVAL { '20'H } -- blank
		::= { cdx6500SPCTXDLCMX25StnEntry 11 }
			
	cdx6500xdlcmx25CUG OBJECT-TYPE
		SYNTAX		DisplayString (SIZE(0..23))
		ACCESS		read-only
		STATUS		mandatory
		DESCRIPTION
			"The port may be a member of up to 8 different Closed User Groups
			(CUGs). Each CUG membership must be a two digit number (except --)
			and separated by a comma. ( e.g. 12,34,56,09,02,03 ).

			  --    - No CUG Membership
			  00-99 - CUG Membership"
		::= { cdx6500SPCTXDLCMX25StnEntry 12 }
			
	cdx6500xdlcmx25BillingRecords OBJECT-TYPE
		SYNTAX		INTEGER	{
					off(0),
					on(1)
					}
		ACCESS		read-only
		STATUS		mandatory
		DESCRIPTION
			"This controls whether billing (accounting) records will be created for
			calls on this port."
		::= { cdx6500SPCTXDLCMX25StnEntry 13 }
			
	cdx6500xdlcmx25UpperQueue OBJECT-TYPE
		SYNTAX		INTEGER (5..15)
		ACCESS		read-only
		STATUS		mandatory
		DESCRIPTION
			"This is the maximum number of data packets a channel on this port will
			queue for transmission before invoking flow control to the attached
			channel"
		DEFVAL { 5 }
		::= { cdx6500SPCTXDLCMX25StnEntry 14 }
			
	cdx6500xdlcmx25LowerQueue OBJECT-TYPE
		SYNTAX		INTEGER (0..4)
		ACCESS		read-only
		STATUS		mandatory
		DESCRIPTION
			"This is the number of data packets a channel on this port will
			have queued for transmission when it releases flow control to the
			attached channel"
		DEFVAL { 0 }
		::= { cdx6500SPCTXDLCMX25StnEntry 15 }




	-- The XDLC Station Statistics Tables
	-- These tables contain Statistics paramaters 
	-- for the XDLC Station table.
			
	cdx6500SPSTXDLCStationTable OBJECT IDENTIFIER ::= { cdx6500PSTStationProtocolGroup 5 }




	-- The XDLC SDLC Station Statistics Table
	-- This table contains Statistics paramaters 
	-- for the XDLC Station table, specific to SDLC stations.
			
	cdx6500SPSTXDLCSDLCStnTable OBJECT-TYPE
		SYNTAX		SEQUENCE OF Cdx6500SPSTXDLCSDLCStnEntry
		ACCESS		not-accessible
		STATUS		mandatory
		DESCRIPTION
			"All of the statistics parameters relevant
			 to the XDLC SDLC Station table."
		::= { cdx6500SPSTXDLCStationTable 1 }
			
	cdx6500SPSTXDLCSDLCStnEntry OBJECT-TYPE
		SYNTAX		Cdx6500SPSTXDLCSDLCStnEntry
		ACCESS		not-accessible
		STATUS		mandatory
		DESCRIPTION
			"A row of XDLC SDLC Station statistics parameters."
		INDEX	{ cdx6500xdlcsStatsPortNum, cdx6500xdlcsStatsStationNum }
		::= { cdx6500SPSTXDLCSDLCStnTable 1 }
			
	Cdx6500SPSTXDLCSDLCStnEntry ::=
		SEQUENCE {
			cdx6500xdlcsdlcStatsPortNum
				INTEGER,
			cdx6500xdlcsdlcStatsStationNum
				INTEGER,
			cdx6500xdlcsdlcUtilizationIn
				INTEGER,
			cdx6500xdlcsdlcUtilizationOut
				INTEGER,
			cdx6500xdlcsdlcCharInTotal
				Counter,
			cdx6500xdlcsdlcCharOutTotal
				Counter,
			cdx6500xdlcsdlcCharsInPerSec
				INTEGER,
			cdx6500xdlcsdlcCharsOutPerSec
				INTEGER,
			cdx6500xdlcsdlcPacketsQueued
				INTEGER,
			cdx6500xdlcsdlcFrameInTotal
				Counter,
			cdx6500xdlcsdlcFrameOutTotal
				Counter,
			cdx6500xdlcsdlcFramesInPerSec
				INTEGER,
			cdx6500xdlcsdlcFramesOutPerSec
				INTEGER,
			cdx6500xdlcsdlcRNRFramesIn
				Counter,
			cdx6500xdlcsdlcRNRFramesOut
				Counter,
			cdx6500xdlcsdlcRRFramesIn
				Counter,
			cdx6500xdlcsdlcRRFramesOut
				Counter,
			cdx6500xdlcsdlcREJFramesIn
				Counter,
			cdx6500xdlcsdlcREJFramesOut
				Counter,
			cdx6500xdlcsdlcQLLCState
				DisplayString,
			cdx6500xdlcsdlcQRRIn
				Counter16,
			cdx6500xdlcsdlcQRROut
				Counter16,
			cdx6500xdlcsdlcSNRMInFrames
				Counter,
			cdx6500xdlcsdlcSNRMOutFrames
				Counter,
			cdx6500xdlcsdlcUAInFrames
				Counter,
			cdx6500xdlcsdlcUAOutFrames
				Counter,
			cdx6500xdlcsdlcDMInFrames
				Counter,
			cdx6500xdlcsdlcDMOutFrames
				Counter,
			cdx6500xdlcsdlcXIDInFrames
				Counter,
			cdx6500xdlcsdlcXIDOutFrames
				Counter,
			cdx6500xdlcsdlcDISCInFrames
				Counter,
			cdx6500xdlcsdlcDISCOutFrames
				Counter,
			cdx6500xdlcsdlcRDInFrames
				Counter,
			cdx6500xdlcsdlcRDOutFrames
				Counter,
			cdx6500xdlcsdlcFRMRInFrames
				Counter,
			cdx6500xdlcsdlcFRMROutFrames
				Counter,
			cdx6500xdlcsdlcUPInFrames
				Counter,
			cdx6500xdlcsdlcUPOutFrames
				Counter,
			cdx6500xdlcsdlcTESTInFrames
				Counter,
			cdx6500xdlcsdlcTESTOutFrames
				Counter,
			cdx6500xdlcsdlcQSMInFrames
				Counter16,
			cdx6500xdlcsdlcQSMOutFrames
				Counter16,
			cdx6500xdlcsdlcQUAInFrames
				Counter16,
			cdx6500xdlcsdlcQUAOutFrames
				Counter16,
			cdx6500xdlcsdlcQRDInFrames
				Counter16,
			cdx6500xdlcsdlcQRDOutFrames
				Counter16,
			cdx6500xdlcsdlcQFRMRInFrames
				Counter16,
			cdx6500xdlcsdlcQFRMROutFrames
				Counter16,
			cdx6500xdlcsdlcQXIDInFrames
				Counter16,
			cdx6500xdlcsdlcQXIDOutFrames
				Counter16,
			cdx6500xdlcsdlcQDCInFrames
				Counter16,
			cdx6500xdlcsdlcQDCOutFrames
				Counter16,
			cdx6500xdlcsdlcQDMInFrames
				Counter16,
			cdx6500xdlcsdlcQDMOutFrames
				Counter16,
			cdx6500xdlcsdlcQTESTInFrames
				Counter16,
			cdx6500xdlcsdlcQTESTOutFrames
				Counter16
			}
			
	cdx6500xdlcsdlcStatsPortNum OBJECT-TYPE
		SYNTAX		INTEGER (1..54)
		ACCESS		read-only
		STATUS		mandatory
		DESCRIPTION
			"Refers to the physical port number."
		::= { cdx6500SPSTXDLCSDLCStnEntry 1 }
			
	cdx6500xdlcsdlcStatsStationNum OBJECT-TYPE
		SYNTAX		INTEGER (1..4)
		ACCESS		read-only
		STATUS		mandatory
		DESCRIPTION
			"Station reference number."
		::= { cdx6500SPSTXDLCSDLCStnEntry 2 }
			
	cdx6500xdlcsdlcUtilizationIn OBJECT-TYPE
		SYNTAX		INTEGER (0..100)
		ACCESS		read-only
		STATUS		mandatory
		DESCRIPTION
			"Indicates the percentage of station resources currently in use from
			the line to the port."
		::= { cdx6500SPSTXDLCSDLCStnEntry 3 }
			
	cdx6500xdlcsdlcUtilizationOut OBJECT-TYPE
		SYNTAX		INTEGER (0..100)
		ACCESS		read-only
		STATUS		mandatory
		DESCRIPTION
			"Indicates the percentage of station resources currently in use from
			the port to the line."
		::= { cdx6500SPSTXDLCSDLCStnEntry 4 }
			
	cdx6500xdlcsdlcCharInTotal OBJECT-TYPE
		SYNTAX		Counter
		ACCESS		read-only
		STATUS		mandatory
		DESCRIPTION
			"Total number of characters processed until now, not including
			header characters."
		::= { cdx6500SPSTXDLCSDLCStnEntry 5 }
			
	cdx6500xdlcsdlcCharOutTotal OBJECT-TYPE
		SYNTAX		Counter
		ACCESS		read-only
		STATUS		mandatory
		DESCRIPTION
			"Total number of characters processed until now, not including
			header characters."
		::= { cdx6500SPSTXDLCSDLCStnEntry 6 }
			
	cdx6500xdlcsdlcCharsInPerSec OBJECT-TYPE
		SYNTAX		INTEGER
		ACCESS		read-only
		STATUS		mandatory
		DESCRIPTION
			"The average number of characters received per second."
		::= { cdx6500SPSTXDLCSDLCStnEntry 7 }
			
	cdx6500xdlcsdlcCharsOutPerSec OBJECT-TYPE
		SYNTAX		INTEGER
		ACCESS		read-only
		STATUS		mandatory
		DESCRIPTION
			"The average number of characters transmitted per second."
		::= { cdx6500SPSTXDLCSDLCStnEntry 8 }
			
	cdx6500xdlcsdlcPacketsQueued OBJECT-TYPE
		SYNTAX		INTEGER
		ACCESS		read-only
		STATUS		mandatory
		DESCRIPTION
			"The total number of packets queued at the SDLC protocol layer."
		::= { cdx6500SPSTXDLCSDLCStnEntry 9 }
			
	cdx6500xdlcsdlcFrameInTotal OBJECT-TYPE
		SYNTAX		Counter
		ACCESS		read-only
		STATUS		mandatory
		DESCRIPTION
			"Total number of MX25 and SDLC frames processed until now."
		::= { cdx6500SPSTXDLCSDLCStnEntry 10 }
			
	cdx6500xdlcsdlcFrameOutTotal OBJECT-TYPE
		SYNTAX		Counter
		ACCESS		read-only
		STATUS		mandatory
		DESCRIPTION
			"Total number of MX25 and SDLC frames processed until now."
		::= { cdx6500SPSTXDLCSDLCStnEntry 11 }
			
	cdx6500xdlcsdlcFramesInPerSec OBJECT-TYPE
		SYNTAX		INTEGER
		ACCESS		read-only
		STATUS		mandatory
		DESCRIPTION
			"The average number of frames received per second."
		::= { cdx6500SPSTXDLCSDLCStnEntry 12 }
			
	cdx6500xdlcsdlcFramesOutPerSec OBJECT-TYPE
		SYNTAX		INTEGER
		ACCESS		read-only
		STATUS		mandatory
		DESCRIPTION
			"The average number of frames transmitted per second."
		::= { cdx6500SPSTXDLCSDLCStnEntry 13 }
			
	cdx6500xdlcsdlcRNRFramesIn OBJECT-TYPE
		SYNTAX		Counter
		ACCESS		read-only
		STATUS		mandatory
		DESCRIPTION
			"Indicates the total number of RNR frames received."
		::= { cdx6500SPSTXDLCSDLCStnEntry 14 }
			
	cdx6500xdlcsdlcRNRFramesOut OBJECT-TYPE
		SYNTAX		Counter
		ACCESS		read-only
		STATUS		mandatory
		DESCRIPTION
			"Indicates the total number of RNR frames transmitted."
		::= { cdx6500SPSTXDLCSDLCStnEntry 15 }
			
	cdx6500xdlcsdlcRRFramesIn OBJECT-TYPE
		SYNTAX		Counter
		ACCESS		read-only
		STATUS		mandatory
		DESCRIPTION
			"Indicates the total number of RR frames received."
		::= { cdx6500SPSTXDLCSDLCStnEntry 16 }
			
	cdx6500xdlcsdlcRRFramesOut OBJECT-TYPE
		SYNTAX		Counter
		ACCESS		read-only
		STATUS		mandatory
		DESCRIPTION
			"Indicates the total number of RR frames transmitted."
		::= { cdx6500SPSTXDLCSDLCStnEntry 17 }
			
	cdx6500xdlcsdlcREJFramesIn OBJECT-TYPE
		SYNTAX		Counter
		ACCESS		read-only
		STATUS		mandatory
		DESCRIPTION
			"Indicates the total number of REJ frames received."
		::= { cdx6500SPSTXDLCSDLCStnEntry 18 }
			
	cdx6500xdlcsdlcREJFramesOut OBJECT-TYPE
		SYNTAX		Counter
		ACCESS		read-only
		STATUS		mandatory
		DESCRIPTION
			"Indicates the total number of REJ frames transmitted."
		::= { cdx6500SPSTXDLCSDLCStnEntry 19 }
			
	cdx6500xdlcsdlcQLLCState OBJECT-TYPE
		SYNTAX		DisplayString (SIZE(0..255))
		ACCESS		read-only
		STATUS		mandatory
		DESCRIPTION
			"Indicates the status of the QLLC layer:

			INOPERATIVE: Noconnection exists with the station.
			CLOSED: Call connected.
			OPENING: Setting up session.
			OPENED: Ready for operation.
			CLOSING: Disconnect in process."
		::= { cdx6500SPSTXDLCSDLCStnEntry 20 }
			
	cdx6500xdlcsdlcQRRIn OBJECT-TYPE
		SYNTAX		Counter16
		ACCESS		read-only
		STATUS		mandatory
		DESCRIPTION
			"Total number of QRR packets received until now."
		::= { cdx6500SPSTXDLCSDLCStnEntry 21 }
			
	cdx6500xdlcsdlcQRROut OBJECT-TYPE
		SYNTAX		Counter16
		ACCESS		read-only
		STATUS		mandatory
		DESCRIPTION
			"Total number of QRR packets transmitted until now."
		::= { cdx6500SPSTXDLCSDLCStnEntry 22 }

	cdx6500xdlcsdlcSNRMInFrames OBJECT-TYPE
		SYNTAX		Counter
		ACCESS		read-only
		STATUS		mandatory
		DESCRIPTION
			"Total number of SNRM frames received until the present time."
		::= { cdx6500SPSTXDLCSDLCStnEntry 23 }

	cdx6500xdlcsdlcSNRMOutFrames OBJECT-TYPE
		SYNTAX		Counter
		ACCESS		read-only
		STATUS		mandatory
		DESCRIPTION
			"Total number of SNRM frames transmitted until the present time."
		::= { cdx6500SPSTXDLCSDLCStnEntry 24 }

	cdx6500xdlcsdlcUAInFrames OBJECT-TYPE
		SYNTAX		Counter
		ACCESS		read-only
		STATUS		mandatory
		DESCRIPTION
			"Total number of UA frames received until the present time."
		::= { cdx6500SPSTXDLCSDLCStnEntry 25 }

	cdx6500xdlcsdlcUAOutFrames OBJECT-TYPE
		SYNTAX		Counter
		ACCESS		read-only
		STATUS		mandatory
		DESCRIPTION
			"Total number of UA frames transmitted until the present time."
		::= { cdx6500SPSTXDLCSDLCStnEntry 26 }

	cdx6500xdlcsdlcDMInFrames OBJECT-TYPE
		SYNTAX		Counter
		ACCESS		read-only
		STATUS		mandatory
		DESCRIPTION
			"Total number of DM frames received until the present time."
		::= { cdx6500SPSTXDLCSDLCStnEntry 27 }

	cdx6500xdlcsdlcDMOutFrames OBJECT-TYPE
		SYNTAX		Counter
		ACCESS		read-only
		STATUS		mandatory
		DESCRIPTION
			"Total number of DM frames transmitted until the present time."
		::= { cdx6500SPSTXDLCSDLCStnEntry 28 }

	cdx6500xdlcsdlcXIDInFrames OBJECT-TYPE
		SYNTAX		Counter
		ACCESS		read-only
		STATUS		mandatory
		DESCRIPTION
			"Total number of XID frames received until the present time."
		::= { cdx6500SPSTXDLCSDLCStnEntry 29 }

	cdx6500xdlcsdlcXIDOutFrames OBJECT-TYPE
		SYNTAX		Counter
		ACCESS		read-only
		STATUS		mandatory
		DESCRIPTION
			"Total number of XID frames transmitted until the present time."
		::= { cdx6500SPSTXDLCSDLCStnEntry 30 }

	cdx6500xdlcsdlcDISCInFrames OBJECT-TYPE
		SYNTAX		Counter
		ACCESS		read-only
		STATUS		mandatory
		DESCRIPTION
			"Total number of DISC frames received until the present time."
		::= { cdx6500SPSTXDLCSDLCStnEntry 31 }

	cdx6500xdlcsdlcDISCOutFrames OBJECT-TYPE
		SYNTAX		Counter
		ACCESS		read-only
		STATUS		mandatory
		DESCRIPTION
			"Total number of DISC frames transmitted until the present time."
		::= { cdx6500SPSTXDLCSDLCStnEntry 32 }

	cdx6500xdlcsdlcRDInFrames OBJECT-TYPE
		SYNTAX		Counter
		ACCESS		read-only
		STATUS		mandatory
		DESCRIPTION
			"Total number of RD frames received until the present time."
		::= { cdx6500SPSTXDLCSDLCStnEntry 33 }

	cdx6500xdlcsdlcRDOutFrames OBJECT-TYPE
		SYNTAX		Counter
		ACCESS		read-only
		STATUS		mandatory
		DESCRIPTION
			"Total number of RD frames transmitted until the present time."
		::= { cdx6500SPSTXDLCSDLCStnEntry 34 }

	cdx6500xdlcsdlcFRMRInFrames OBJECT-TYPE
		SYNTAX		Counter
		ACCESS		read-only
		STATUS		mandatory
		DESCRIPTION
			"Total number of FRMR frames received until the present time."
		::= { cdx6500SPSTXDLCSDLCStnEntry 35 }

	cdx6500xdlcsdlcFRMROutFrames OBJECT-TYPE
		SYNTAX		Counter
		ACCESS		read-only
		STATUS		mandatory
		DESCRIPTION
			"Total number of FRMR frames transmitted until the present time."
		::= { cdx6500SPSTXDLCSDLCStnEntry 36 }

	cdx6500xdlcsdlcUPInFrames OBJECT-TYPE
		SYNTAX		Counter
		ACCESS		read-only
		STATUS		mandatory
		DESCRIPTION
			"Total number of UP frames received until the present time."
		::= { cdx6500SPSTXDLCSDLCStnEntry 37 }

	cdx6500xdlcsdlcUPOutFrames OBJECT-TYPE
		SYNTAX		Counter
		ACCESS		read-only
		STATUS		mandatory
		DESCRIPTION
			"Total number of UP frames transmitted until the present time."
		::= { cdx6500SPSTXDLCSDLCStnEntry 38 }

	cdx6500xdlcsdlcTESTInFrames OBJECT-TYPE
		SYNTAX		Counter
		ACCESS		read-only
		STATUS		mandatory
		DESCRIPTION
			"Total number of TEST frames received until the present time."
		::= { cdx6500SPSTXDLCSDLCStnEntry 39 }

	cdx6500xdlcsdlcTESTOutFrames OBJECT-TYPE
		SYNTAX		Counter
		ACCESS		read-only
		STATUS		mandatory
		DESCRIPTION
			"Total number of TEST frames transmitted until the present time."
		::= { cdx6500SPSTXDLCSDLCStnEntry 40 }

	cdx6500xdlcsdlcQSMInFrames OBJECT-TYPE
		SYNTAX		Counter16
		ACCESS		read-only
		STATUS		mandatory
		DESCRIPTION
			"Total number of QSM packets received until the present time."
		::= { cdx6500SPSTXDLCSDLCStnEntry 41 }

	cdx6500xdlcsdlcQSMOutFrames OBJECT-TYPE
		SYNTAX		Counter16
		ACCESS		read-only
		STATUS		mandatory
		DESCRIPTION
			"Total number of QSM packets transmitted until the present time."
		::= { cdx6500SPSTXDLCSDLCStnEntry 42 }

	cdx6500xdlcsdlcQUAInFrames OBJECT-TYPE
		SYNTAX		Counter16
		ACCESS		read-only
		STATUS		mandatory
		DESCRIPTION
			"Total number of QUA packets received until the present time."
		::= { cdx6500SPSTXDLCSDLCStnEntry 43 }

	cdx6500xdlcsdlcQUAOutFrames OBJECT-TYPE
		SYNTAX		Counter16
		ACCESS		read-only
		STATUS		mandatory
		DESCRIPTION
			"Total number of QUA packets transmitted until the present time."
		::= { cdx6500SPSTXDLCSDLCStnEntry 44 }

	cdx6500xdlcsdlcQRDInFrames OBJECT-TYPE
		SYNTAX		Counter16
		ACCESS		read-only
		STATUS		mandatory
		DESCRIPTION
			"Total number of QRD packets received until the present time."
		::= { cdx6500SPSTXDLCSDLCStnEntry 45 }

	cdx6500xdlcsdlcQRDOutFrames OBJECT-TYPE
		SYNTAX		Counter16
		ACCESS		read-only
		STATUS		mandatory
		DESCRIPTION
			"Total number of QRD packets transmitted until the present time."
		::= { cdx6500SPSTXDLCSDLCStnEntry 46 }

	cdx6500xdlcsdlcQFRMRInFrames OBJECT-TYPE
		SYNTAX		Counter16
		ACCESS		read-only
		STATUS		mandatory
		DESCRIPTION
			"Total number of QFRMR packets received until the present time."
		::= { cdx6500SPSTXDLCSDLCStnEntry 47 }

	cdx6500xdlcsdlcQFRMROutFrames OBJECT-TYPE
		SYNTAX		Counter16
		ACCESS		read-only
		STATUS		mandatory
		DESCRIPTION
			"Total number of QFRMR packets transmitted until the present time."
		::= { cdx6500SPSTXDLCSDLCStnEntry 48 }

	cdx6500xdlcsdlcQXIDInFrames OBJECT-TYPE
		SYNTAX		Counter16
		ACCESS		read-only
		STATUS		mandatory
		DESCRIPTION
			"Total number of QXID packets received until the present time."
		::= { cdx6500SPSTXDLCSDLCStnEntry 49 }

	cdx6500xdlcsdlcQXIDOutFrames OBJECT-TYPE
		SYNTAX		Counter16
		ACCESS		read-only
		STATUS		mandatory
		DESCRIPTION
			"Total number of QXID packets transmitted until the present time."
		::= { cdx6500SPSTXDLCSDLCStnEntry 50 }

	cdx6500xdlcsdlcQDCInFrames OBJECT-TYPE
		SYNTAX		Counter16
		ACCESS		read-only
		STATUS		mandatory
		DESCRIPTION
			"Total number of QDC packets received until the present time."
		::= { cdx6500SPSTXDLCSDLCStnEntry 51 }

	cdx6500xdlcsdlcQDCOutFrames OBJECT-TYPE
		SYNTAX		Counter16
		ACCESS		read-only
		STATUS		mandatory
		DESCRIPTION
			"Total number of QDC packets transmitted until the present time."
		::= { cdx6500SPSTXDLCSDLCStnEntry 52 }

	cdx6500xdlcsdlcQDMInFrames OBJECT-TYPE
		SYNTAX		Counter16
		ACCESS		read-only
		STATUS		mandatory
		DESCRIPTION
			"Total number of QDM packets received until the present time."
		::= { cdx6500SPSTXDLCSDLCStnEntry 53 }

	cdx6500xdlcsdlcQDMOutFrames OBJECT-TYPE
		SYNTAX		Counter16
		ACCESS		read-only
		STATUS		mandatory
		DESCRIPTION
			"Total number of QDM packets transmitted until the present time."
		::= { cdx6500SPSTXDLCSDLCStnEntry 54 }

	cdx6500xdlcsdlcQTESTInFrames OBJECT-TYPE
		SYNTAX		Counter16
		ACCESS		read-only
		STATUS		mandatory
		DESCRIPTION
			"Total number of QTEST packets received until the present time."
		::= { cdx6500SPSTXDLCSDLCStnEntry 55 }

	cdx6500xdlcsdlcQTESTOutFrames OBJECT-TYPE
		SYNTAX		Counter16
		ACCESS		read-only
		STATUS		mandatory
		DESCRIPTION
			"Total number of QTEST packets transmitted until the present time."
		::= { cdx6500SPSTXDLCSDLCStnEntry 56 }




	-- The XDLC MX.25 Station Statistics Table
	-- This table contains Statistics paramaters 
	-- for the XDLC Station table, specific to MX.25 stations.
			
	cdx6500SPSTXDLCMX25StnTable OBJECT-TYPE
		SYNTAX		SEQUENCE OF Cdx6500SPSTXDLCMX25StnEntry
		ACCESS		not-accessible
		STATUS		mandatory
		DESCRIPTION
			"All of the statistics parameters relevant
			 to the XDLC MX.25 Station table."
		::= { cdx6500SPSTXDLCStationTable 2 }
			
	cdx6500SPSTXDLCMX25StnEntry OBJECT-TYPE
		SYNTAX		Cdx6500SPSTXDLCMX25StnEntry
		ACCESS		not-accessible
		STATUS		mandatory
		DESCRIPTION
			"A row of XDLC MX.25 Station statistics parameters."
		INDEX	{ cdx6500xdlcsStatsPortNum, cdx6500xdlcsStatsStationNum }
		::= { cdx6500SPSTXDLCMX25StnTable 1 }
			
	Cdx6500SPSTXDLCMX25StnEntry ::=
		SEQUENCE {
			cdx6500xdlcmx25StatsPortNum
				INTEGER,
			cdx6500xdlcmx25StatsStationNum
				INTEGER,
			cdx6500xdlcmx25UtilizationIn
				INTEGER,
			cdx6500xdlcmx25UtilizationOut
				INTEGER,
			cdx6500xdlcmx25CharInTotal
				Counter,
			cdx6500xdlcmx25CharOutTotal
				Counter,
			cdx6500xdlcmx25CharsInPerSec
				INTEGER,
			cdx6500xdlcmx25CharsOutPerSec
				INTEGER,
			cdx6500xdlcmx25PktInTotal
				Counter,
			cdx6500xdlcmx25PktOutTotal
				Counter,
			cdx6500xdlcmx25PktsInPerSec
				INTEGER,
			cdx6500xdlcmx25PktsOutPerSec
				INTEGER,
			cdx6500xdlcmx25PacketsQueued
				INTEGER,
			cdx6500xdlcmx25FrameInTotal
				Counter,
			cdx6500xdlcmx25FrameOutTotal
				Counter,
			cdx6500xdlcmx25FramesInPerSec
				INTEGER,
			cdx6500xdlcmx25FramesOutPerSec
				INTEGER,
			cdx6500xdlcmx25RNRFramesIn
				Counter,
			cdx6500xdlcmx25RNRFramesOut
				Counter,
			cdx6500xdlcmx25RRFramesIn
				Counter,
			cdx6500xdlcmx25RRFramesOut
				Counter,
			cdx6500xdlcmx25REJFramesIn
				Counter,
			cdx6500xdlcmx25REJFramesOut
				Counter,
			cdx6500xdlcmx25DataPktsIn
				Counter,
			cdx6500xdlcmx25DataPktsOut
				Counter,
			cdx6500xdlcmx25MaxSVC
				INTEGER,
			cdx6500xdlcmx25CurrentSVC
				INTEGER,
			cdx6500xdlcmx25MaxPVC
				INTEGER,
			cdx6500xdlcmx25CurrentPVC
				INTEGER,
			cdx6500xdlcmx25InfoInFrames
				Counter,
			cdx6500xdlcmx25InfoOutFrames
				Counter,
			cdx6500xdlcmx25SNRMInFrames
				Counter,
			cdx6500xdlcmx25SNRMOutFrames
				Counter,
			cdx6500xdlcmx25UAInFrames
				Counter,
			cdx6500xdlcmx25UAOutFrames
				Counter,
			cdx6500xdlcmx25FRMRInFrames
				Counter,
			cdx6500xdlcmx25FRMROutFrames
				Counter,
			cdx6500xdlcmx25RRInPkts
				Counter,
			cdx6500xdlcmx25RROutPkts
				Counter,
			cdx6500xdlcmx25RNRInPkts
				Counter,
			cdx6500xdlcmx25RNROutPkts
				Counter,
			cdx6500xdlcmx25REJInPkts
				Counter,
			cdx6500xdlcmx25REJOutPkts
				Counter,
			cdx6500xdlcmx25InCallReqs
				Counter,
			cdx6500xdlcmx25OutCallReqs
				Counter,
			cdx6500xdlcmx25InCallAccepts
				Counter,
			cdx6500xdlcmx25OutCallAccepts
				Counter,
			cdx6500xdlcmx25InClearReqs
				Counter,
			cdx6500xdlcmx25OutClearReqs
				Counter,
			cdx6500xdlcmx25InClearConfs
				Counter,
			cdx6500xdlcmx25OutClearConfs
				Counter,
			cdx6500xdlcmx25InInterruptReqs
				Counter,
			cdx6500xdlcmx25OutInterruptReqs
				Counter,
			cdx6500xdlcmx25InInterruptConfs
				Counter,
			cdx6500xdlcmx25OutInterruptConfs
				Counter,
			cdx6500xdlcmx25InResetReqs
				Counter,
			cdx6500xdlcmx25OutResetReqs
				Counter,
			cdx6500xdlcmx25InResetConfs
				Counter,
			cdx6500xdlcmx25OutResetConfs
				Counter,
			cdx6500xdlcmx25InRestartReqs
				Counter,
			cdx6500xdlcmx25OutRestartReqs
				Counter,
			cdx6500xdlcmx25InRestartConfs
				Counter,
			cdx6500xdlcmx25OutRestartConfs
				Counter,
			cdx6500xdlcmx25LastInLCN
				INTEGER,
			cdx6500xdlcmx25InStatus
				DisplayString,
			cdx6500xdlcmx25LICBPCalledAddr
				DisplayString,
			cdx6500xdlcmx25LICBPCallingAddr
				DisplayString,
			cdx6500xdlcmx25LICBPFacilities
				DisplayString,
			cdx6500xdlcmx25LICBPCUD
				DisplayString,
			cdx6500xdlcmx25LICAPCalledAddr
				DisplayString,
			cdx6500xdlcmx25LICAPCallingAddr
				DisplayString,
			cdx6500xdlcmx25LICAPFacilities
				DisplayString,
			cdx6500xdlcmx25LICAPCUD
				DisplayString,
			cdx6500xdlcmx25LastOutLCN
				INTEGER,
			cdx6500xdlcmx25OutStatus
				DisplayString,
			cdx6500xdlcmx25LOCBPCalledAddr
				DisplayString,
			cdx6500xdlcmx25LOCBPCallingAddr
				DisplayString,
			cdx6500xdlcmx25LOCBPFacilities
				DisplayString,
			cdx6500xdlcmx25LOCBPCUD
				DisplayString,
			cdx6500xdlcmx25LOCAPCalledAddr
				DisplayString,
			cdx6500xdlcmx25LOCAPCallingAddr
				DisplayString,
			cdx6500xdlcmx25LOCAPFacilities
				DisplayString,
			cdx6500xdlcmx25LOCAPCUD
				DisplayString
			}
			
	cdx6500xdlcmx25StatsPortNum OBJECT-TYPE
		SYNTAX		INTEGER (1..54)
		ACCESS		read-only
		STATUS		mandatory
		DESCRIPTION
			"Refers to the physical port number."
		::= { cdx6500SPSTXDLCMX25StnEntry 1 }
			
	cdx6500xdlcmx25StatsStationNum OBJECT-TYPE
		SYNTAX		INTEGER (1..4)
		ACCESS		read-only
		STATUS		mandatory
		DESCRIPTION
			"Station reference number."
		::= { cdx6500SPSTXDLCMX25StnEntry 2 }
			
	cdx6500xdlcmx25UtilizationIn OBJECT-TYPE
		SYNTAX		INTEGER (0..100)
		ACCESS		read-only
		STATUS		mandatory
		DESCRIPTION
			"Indicates the percentage of station resources currently in use from
			the line to the port."
		::= { cdx6500SPSTXDLCMX25StnEntry 3 }
			
	cdx6500xdlcmx25UtilizationOut OBJECT-TYPE
		SYNTAX		INTEGER (0..100)
		ACCESS		read-only
		STATUS		mandatory
		DESCRIPTION
			"Indicates the percentage of station resources currently in use from
			the port to the line."
		::= { cdx6500SPSTXDLCMX25StnEntry 4 }
			
	cdx6500xdlcmx25CharInTotal OBJECT-TYPE
		SYNTAX		Counter
		ACCESS		read-only
		STATUS		mandatory
		DESCRIPTION
			"Total number of characters processed until now, not including
			frame and packet headers."
		::= { cdx6500SPSTXDLCMX25StnEntry 5 }
			
	cdx6500xdlcmx25CharOutTotal OBJECT-TYPE
		SYNTAX		Counter
		ACCESS		read-only
		STATUS		mandatory
		DESCRIPTION
			"Total number of characters processed until now, not including
			frame and packet headers."
		::= { cdx6500SPSTXDLCMX25StnEntry 6 }
			
	cdx6500xdlcmx25CharsInPerSec OBJECT-TYPE
		SYNTAX		INTEGER
		ACCESS		read-only
		STATUS		mandatory
		DESCRIPTION
			"The average number of characters received per second 
			 during the previous minute."
		::= { cdx6500SPSTXDLCMX25StnEntry 7 }
			
	cdx6500xdlcmx25CharsOutPerSec OBJECT-TYPE
		SYNTAX		INTEGER
		ACCESS		read-only
		STATUS		mandatory
		DESCRIPTION
			"The average number of characters transmitted per second 
			 during the previous minute."
		::= { cdx6500SPSTXDLCMX25StnEntry 8 }
			
	cdx6500xdlcmx25PktInTotal OBJECT-TYPE
		SYNTAX		Counter
		ACCESS		read-only
		STATUS		mandatory
		DESCRIPTION
			"Total number of data packets passed through the station."
		::= { cdx6500SPSTXDLCMX25StnEntry 9 }
			
	cdx6500xdlcmx25PktOutTotal OBJECT-TYPE
		SYNTAX		Counter
		ACCESS		read-only
		STATUS		mandatory
		DESCRIPTION
			"Total number of data packets passed through the station."
		::= { cdx6500SPSTXDLCMX25StnEntry 10 }
			
	cdx6500xdlcmx25PktsInPerSec OBJECT-TYPE
		SYNTAX		INTEGER
		ACCESS		read-only
		STATUS		mandatory
		DESCRIPTION
			"The average number of packets received per second 
			 during the previous minute."
		::= { cdx6500SPSTXDLCMX25StnEntry 11 }
			
	cdx6500xdlcmx25PktsOutPerSec OBJECT-TYPE
		SYNTAX		INTEGER
		ACCESS		read-only
		STATUS		mandatory
		DESCRIPTION
			"The average number of packets transmitted per second 
			 during the previous minute."
		::= { cdx6500SPSTXDLCMX25StnEntry 12 }
			
	cdx6500xdlcmx25PacketsQueued OBJECT-TYPE
		SYNTAX		INTEGER
		ACCESS		read-only
		STATUS		mandatory
		DESCRIPTION
			"Total number of packets queued at the MX25 protocol layer."
		::= { cdx6500SPSTXDLCMX25StnEntry 13 }
			
	cdx6500xdlcmx25FrameInTotal OBJECT-TYPE
		SYNTAX		Counter
		ACCESS		read-only
		STATUS		mandatory
		DESCRIPTION
			"Total number of frames processed until now."
		::= { cdx6500SPSTXDLCMX25StnEntry 14 }
			
	cdx6500xdlcmx25FrameOutTotal OBJECT-TYPE
		SYNTAX		Counter
		ACCESS		read-only
		STATUS		mandatory
		DESCRIPTION
			"Total number of frames processed until now."
		::= { cdx6500SPSTXDLCMX25StnEntry 15 }
			
	cdx6500xdlcmx25FramesInPerSec OBJECT-TYPE
		SYNTAX		INTEGER
		ACCESS		read-only
		STATUS		mandatory
		DESCRIPTION
			"The average number of frames received per second 
			 during the previous minute."
		::= { cdx6500SPSTXDLCMX25StnEntry 16 }
			
	cdx6500xdlcmx25FramesOutPerSec OBJECT-TYPE
		SYNTAX		INTEGER
		ACCESS		read-only
		STATUS		mandatory
		DESCRIPTION
			"The average number of frames transmitted per second 
			 during the previous minute."
		::= { cdx6500SPSTXDLCMX25StnEntry 17 }
			
	cdx6500xdlcmx25RNRFramesIn OBJECT-TYPE
		SYNTAX		Counter
		ACCESS		read-only
		STATUS		mandatory
		DESCRIPTION
			"Indicates the total number of RNR frames received."
		::= { cdx6500SPSTXDLCMX25StnEntry 18 }
			
	cdx6500xdlcmx25RNRFramesOut OBJECT-TYPE
		SYNTAX		Counter
		ACCESS		read-only
		STATUS		mandatory
		DESCRIPTION
			"Indicates the total number of RNR frames transmitted."
		::= { cdx6500SPSTXDLCMX25StnEntry 19 }
			
	cdx6500xdlcmx25RRFramesIn OBJECT-TYPE
		SYNTAX		Counter
		ACCESS		read-only
		STATUS		mandatory
		DESCRIPTION
			"Indicates the total number of RR frames received."
		::= { cdx6500SPSTXDLCMX25StnEntry 20 }
			
	cdx6500xdlcmx25RRFramesOut OBJECT-TYPE
		SYNTAX		Counter
		ACCESS		read-only
		STATUS		mandatory
		DESCRIPTION
			"Indicates the total number of RR frames transmitted."
		::= { cdx6500SPSTXDLCMX25StnEntry 21 }
			
	cdx6500xdlcmx25REJFramesIn OBJECT-TYPE
		SYNTAX		Counter
		ACCESS		read-only
		STATUS		mandatory
		DESCRIPTION
			"Indicates the total number of REJ frames received."
		::= { cdx6500SPSTXDLCMX25StnEntry 22 }
			
	cdx6500xdlcmx25REJFramesOut OBJECT-TYPE
		SYNTAX		Counter
		ACCESS		read-only
		STATUS		mandatory
		DESCRIPTION
			"Indicates the total number of REJ frames transmitted."
		::= { cdx6500SPSTXDLCMX25StnEntry 23 }
			
	cdx6500xdlcmx25DataPktsIn OBJECT-TYPE
		SYNTAX		Counter
		ACCESS		read-only
		STATUS		mandatory
		DESCRIPTION
			"Indicates the total number of packets received."
		::= { cdx6500SPSTXDLCMX25StnEntry 24 }
			
	cdx6500xdlcmx25DataPktsOut OBJECT-TYPE
		SYNTAX		Counter
		ACCESS		read-only
		STATUS		mandatory
		DESCRIPTION
			"Indicates the total number of packets transmitted."
		::= { cdx6500SPSTXDLCMX25StnEntry 25 }

	cdx6500xdlcmx25MaxSVC OBJECT-TYPE
		SYNTAX		INTEGER
		ACCESS		read-only
		STATUS		mandatory
		DESCRIPTION
			"The maximum number SVC channels used by this station."
		::= { cdx6500SPSTXDLCMX25StnEntry 26 }

	cdx6500xdlcmx25CurrentSVC OBJECT-TYPE
		SYNTAX		INTEGER
		ACCESS		read-only
		STATUS		mandatory
		DESCRIPTION
			"The number of SVC channels currently in use."
		::= { cdx6500SPSTXDLCMX25StnEntry 27 }

	cdx6500xdlcmx25MaxPVC OBJECT-TYPE
		SYNTAX		INTEGER
		ACCESS		read-only
		STATUS		mandatory
		DESCRIPTION
			"The maximum number PVC channels used by this station."
		::= { cdx6500SPSTXDLCMX25StnEntry 28 }

	cdx6500xdlcmx25CurrentPVC OBJECT-TYPE
		SYNTAX		INTEGER
		ACCESS		read-only
		STATUS		mandatory
		DESCRIPTION
			"The number of PVC channels currently in use."
		::= { cdx6500SPSTXDLCMX25StnEntry 29 }

	cdx6500xdlcmx25InfoInFrames OBJECT-TYPE
		SYNTAX		Counter
		ACCESS		read-only
		STATUS		mandatory
		DESCRIPTION
			"Indicates the total number of Info frames received."
		::= { cdx6500SPSTXDLCMX25StnEntry 30 }

	cdx6500xdlcmx25InfoOutFrames OBJECT-TYPE
		SYNTAX		Counter
		ACCESS		read-only
		STATUS		mandatory
		DESCRIPTION
			"Indicates the total number of Info frames transmitted."
		::= { cdx6500SPSTXDLCMX25StnEntry 31 }

	cdx6500xdlcmx25SNRMInFrames OBJECT-TYPE
		SYNTAX		Counter
		ACCESS		read-only
		STATUS		mandatory
		DESCRIPTION
			"Indicates the total number of SNRM frames received."
		::= { cdx6500SPSTXDLCMX25StnEntry 32 }

	cdx6500xdlcmx25SNRMOutFrames OBJECT-TYPE
		SYNTAX		Counter
		ACCESS		read-only
		STATUS		mandatory
		DESCRIPTION
			"Indicates the total number of SNRM frames transmitted."
		::= { cdx6500SPSTXDLCMX25StnEntry 33 }

	cdx6500xdlcmx25UAInFrames OBJECT-TYPE
		SYNTAX		Counter
		ACCESS		read-only
		STATUS		mandatory
		DESCRIPTION
			"Indicates the total number of UA frames received."
		::= { cdx6500SPSTXDLCMX25StnEntry 34 }

	cdx6500xdlcmx25UAOutFrames OBJECT-TYPE
		SYNTAX		Counter
		ACCESS		read-only
		STATUS		mandatory
		DESCRIPTION
			"Indicates the total number of UA frames transmitted."
		::= { cdx6500SPSTXDLCMX25StnEntry 35 }

	cdx6500xdlcmx25FRMRInFrames OBJECT-TYPE
		SYNTAX		Counter
		ACCESS		read-only
		STATUS		mandatory
		DESCRIPTION
			"Indicates the total number of FRMR frames received."
		::= { cdx6500SPSTXDLCMX25StnEntry 36 }

	cdx6500xdlcmx25FRMROutFrames OBJECT-TYPE
		SYNTAX		Counter
		ACCESS		read-only
		STATUS		mandatory
		DESCRIPTION
			"Indicates the total number of FRMR frames transmitted."
		::= { cdx6500SPSTXDLCMX25StnEntry 37 }

	cdx6500xdlcmx25RRInPkts OBJECT-TYPE
		SYNTAX		Counter
		ACCESS		read-only
		STATUS		mandatory
		DESCRIPTION
			"Indicates the total number of RR packets received."
		::= { cdx6500SPSTXDLCMX25StnEntry 38 }

	cdx6500xdlcmx25RROutPkts OBJECT-TYPE
		SYNTAX		Counter
		ACCESS		read-only
		STATUS		mandatory
		DESCRIPTION
			"Indicates the total number of RR packets transmitted."
		::= { cdx6500SPSTXDLCMX25StnEntry 39 }

	cdx6500xdlcmx25RNRInPkts OBJECT-TYPE
		SYNTAX		Counter
		ACCESS		read-only
		STATUS		mandatory
		DESCRIPTION
			"Indicates the total number of RNR packets received."
		::= { cdx6500SPSTXDLCMX25StnEntry 40 }

	cdx6500xdlcmx25RNROutPkts OBJECT-TYPE
		SYNTAX		Counter
		ACCESS		read-only
		STATUS		mandatory
		DESCRIPTION
			"Indicates the total number of RNR packets transmitted."
		::= { cdx6500SPSTXDLCMX25StnEntry 41 }

	cdx6500xdlcmx25REJInPkts OBJECT-TYPE
		SYNTAX		Counter
		ACCESS		read-only
		STATUS		mandatory
		DESCRIPTION
			"Indicates the total number of REJ packets received."
		::= { cdx6500SPSTXDLCMX25StnEntry 42 }

	cdx6500xdlcmx25REJOutPkts OBJECT-TYPE
		SYNTAX		Counter
		ACCESS		read-only
		STATUS		mandatory
		DESCRIPTION
			"Indicates the total number of REJ packets transmitted."
		::= { cdx6500SPSTXDLCMX25StnEntry 43 }

	cdx6500xdlcmx25InCallReqs OBJECT-TYPE
		SYNTAX		Counter
		ACCESS		read-only
		STATUS		mandatory
		DESCRIPTION
			"Indicates the total number of Call Request packets received."
		::= { cdx6500SPSTXDLCMX25StnEntry 44 }

	cdx6500xdlcmx25OutCallReqs OBJECT-TYPE
		SYNTAX		Counter
		ACCESS		read-only
		STATUS		mandatory
		DESCRIPTION
			"Indicates the total number of Call Request packets transmitted."
		::= { cdx6500SPSTXDLCMX25StnEntry 45 }

	cdx6500xdlcmx25InCallAccepts OBJECT-TYPE
		SYNTAX		Counter
		ACCESS		read-only
		STATUS		mandatory
		DESCRIPTION
			"Indicates the total number of Call Accept packets received."
		::= { cdx6500SPSTXDLCMX25StnEntry 46 }

	cdx6500xdlcmx25OutCallAccepts OBJECT-TYPE
		SYNTAX		Counter
		ACCESS		read-only
		STATUS		mandatory
		DESCRIPTION
			"Indicates the total number of Call Accept packets transmitted."
		::= { cdx6500SPSTXDLCMX25StnEntry 47 }

	cdx6500xdlcmx25InClearReqs OBJECT-TYPE
		SYNTAX		Counter
		ACCESS		read-only
		STATUS		mandatory
		DESCRIPTION
			"Indicates the total number of Clear Request packets received."
		::= { cdx6500SPSTXDLCMX25StnEntry 48 }

	cdx6500xdlcmx25OutClearReqs OBJECT-TYPE
		SYNTAX		Counter
		ACCESS		read-only
		STATUS		mandatory
		DESCRIPTION
			"Indicates the total number of Clear Request packets transmitted."
		::= { cdx6500SPSTXDLCMX25StnEntry 49 }

	cdx6500xdlcmx25InClearConfs OBJECT-TYPE
		SYNTAX		Counter
		ACCESS		read-only
		STATUS		mandatory
		DESCRIPTION
			"Indicates the total number of Clear confirmation packets received."
		::= { cdx6500SPSTXDLCMX25StnEntry 50 }

	cdx6500xdlcmx25OutClearConfs OBJECT-TYPE
		SYNTAX		Counter
		ACCESS		read-only
		STATUS		mandatory
		DESCRIPTION
			"Indicates the total number of Clear confirmation packets transmitted."
		::= { cdx6500SPSTXDLCMX25StnEntry 51 }

	cdx6500xdlcmx25InInterruptReqs OBJECT-TYPE
		SYNTAX		Counter
		ACCESS		read-only
		STATUS		mandatory
		DESCRIPTION
			"Indicates the total number of Interrupt Request packets received."
		::= { cdx6500SPSTXDLCMX25StnEntry 52 }

	cdx6500xdlcmx25OutInterruptReqs OBJECT-TYPE
		SYNTAX		Counter
		ACCESS		read-only
		STATUS		mandatory
		DESCRIPTION
			"Indicates the total number of Interrupt Request packets transmitted."
		::= { cdx6500SPSTXDLCMX25StnEntry 53 }

	cdx6500xdlcmx25InInterruptConfs OBJECT-TYPE
		SYNTAX		Counter
		ACCESS		read-only
		STATUS		mandatory
		DESCRIPTION
			"Indicates the total number of Interrupt Confimation packets received."
		::= { cdx6500SPSTXDLCMX25StnEntry 54 }

	cdx6500xdlcmx25OutInterruptConfs OBJECT-TYPE
		SYNTAX		Counter
		ACCESS		read-only
		STATUS		mandatory
		DESCRIPTION
			"Indicates the total number of Interrupt Confirmation packets
			transmitted."
		::= { cdx6500SPSTXDLCMX25StnEntry 55 }

	cdx6500xdlcmx25InResetReqs OBJECT-TYPE
		SYNTAX		Counter
		ACCESS		read-only
		STATUS		mandatory
		DESCRIPTION
			"Indicates the total number of Reset Request packets received."
		::= { cdx6500SPSTXDLCMX25StnEntry 56 }

	cdx6500xdlcmx25OutResetReqs OBJECT-TYPE
		SYNTAX		Counter
		ACCESS		read-only
		STATUS		mandatory
		DESCRIPTION
			"Indicates the total number of Reset Request packets transmitted."
		::= { cdx6500SPSTXDLCMX25StnEntry 57 }

	cdx6500xdlcmx25InResetConfs OBJECT-TYPE
		SYNTAX		Counter
		ACCESS		read-only
		STATUS		mandatory
		DESCRIPTION
			"Indicates the total number of Reset Confimation packets received."
		::= { cdx6500SPSTXDLCMX25StnEntry 58 }

	cdx6500xdlcmx25OutResetConfs OBJECT-TYPE
		SYNTAX		Counter
		ACCESS		read-only
		STATUS		mandatory
		DESCRIPTION
			"Indicates the total number of Reset Confirmation packets
			transmitted."
		::= { cdx6500SPSTXDLCMX25StnEntry 59 }

	cdx6500xdlcmx25InRestartReqs OBJECT-TYPE
		SYNTAX		Counter
		ACCESS		read-only
		STATUS		mandatory
		DESCRIPTION
			"Indicates the total number of Restart Request packets received."
		::= { cdx6500SPSTXDLCMX25StnEntry 60 }

	cdx6500xdlcmx25OutRestartReqs OBJECT-TYPE
		SYNTAX		Counter
		ACCESS		read-only
		STATUS		mandatory
		DESCRIPTION
			"Indicates the total number of Restart Request packets transmitted."
		::= { cdx6500SPSTXDLCMX25StnEntry 61 }

	cdx6500xdlcmx25InRestartConfs OBJECT-TYPE
		SYNTAX		Counter
		ACCESS		read-only
		STATUS		mandatory
		DESCRIPTION
			"Indicates the total number of Restart Confimation packets received."
		::= { cdx6500SPSTXDLCMX25StnEntry 62 }

	cdx6500xdlcmx25OutRestartConfs OBJECT-TYPE
		SYNTAX		Counter
		ACCESS		read-only
		STATUS		mandatory
		DESCRIPTION
			"Indicates the total number of Restart Confirmation packets
			transmitted."
		::= { cdx6500SPSTXDLCMX25StnEntry 63 }

	cdx6500xdlcmx25LastInLCN OBJECT-TYPE
		SYNTAX		INTEGER
		ACCESS		read-only
		STATUS		mandatory
		DESCRIPTION
			"Channel number of last inbound call."
		::= { cdx6500SPSTXDLCMX25StnEntry 64 }

	cdx6500xdlcmx25InStatus OBJECT-TYPE
		SYNTAX		DisplayString
		ACCESS		read-only
		STATUS		mandatory
		DESCRIPTION
			"Success: Message has been through the network successfully.

			Process OK, call passed to ROUTE: Inbound call has been processed and
			passed to Route and is being processed.

			Failed processing, call cleared: Inbound message was processed, but
			failed for some reason, and the call has been cleared."
		::= { cdx6500SPSTXDLCMX25StnEntry 65 }

	cdx6500xdlcmx25LICBPCalledAddr OBJECT-TYPE
		SYNTAX		DisplayString
		ACCESS		read-only
		STATUS		mandatory
		DESCRIPTION
			"Last inbound call before processing: the X.25 address that was
			called."
		::= { cdx6500SPSTXDLCMX25StnEntry 66 }

	cdx6500xdlcmx25LICBPCallingAddr OBJECT-TYPE
		SYNTAX		DisplayString
		ACCESS		read-only
		STATUS		mandatory
		DESCRIPTION
			"Last inbound call before processing: the X.25 address that initiated
			the call."
		::= { cdx6500SPSTXDLCMX25StnEntry 67 }

	cdx6500xdlcmx25LICBPFacilities OBJECT-TYPE
		SYNTAX		DisplayString
		ACCESS		read-only
		STATUS		mandatory
		DESCRIPTION
			"Last inbound call before processing: the facilities that were
			requested in the most recent call request packet."
		::= { cdx6500SPSTXDLCMX25StnEntry 68 }

	cdx6500xdlcmx25LICBPCUD OBJECT-TYPE
		SYNTAX		DisplayString
		ACCESS		read-only
		STATUS		mandatory
		DESCRIPTION
			"Last inbound call before processing: Call User Data contains end-user
			or routing information specific to the network."
		::= { cdx6500SPSTXDLCMX25StnEntry 69 }

	cdx6500xdlcmx25LICAPCalledAddr OBJECT-TYPE
		SYNTAX		DisplayString
		ACCESS		read-only
		STATUS		mandatory
		DESCRIPTION
			"Last inbound call after processing: the X.25 address that was
			called."
		::= { cdx6500SPSTXDLCMX25StnEntry 70 }

	cdx6500xdlcmx25LICAPCallingAddr OBJECT-TYPE
		SYNTAX		DisplayString
		ACCESS		read-only
		STATUS		mandatory
		DESCRIPTION
			"Last inbound call after processing: the X.25 address that initiated
			the call."
		::= { cdx6500SPSTXDLCMX25StnEntry 71 }

	cdx6500xdlcmx25LICAPFacilities OBJECT-TYPE
		SYNTAX		DisplayString
		ACCESS		read-only
		STATUS		mandatory
		DESCRIPTION
			"Last inbound call after processing: the facilities that were
			requested in the most recent call request packet."
		::= { cdx6500SPSTXDLCMX25StnEntry 72 }

	cdx6500xdlcmx25LICAPCUD OBJECT-TYPE
		SYNTAX		DisplayString
		ACCESS		read-only
		STATUS		mandatory
		DESCRIPTION
			"Last inbound call after processing: Call User Data contains end-user
			or routing information specific to the network."
		::= { cdx6500SPSTXDLCMX25StnEntry 73 }

	cdx6500xdlcmx25LastOutLCN OBJECT-TYPE
		SYNTAX		INTEGER
		ACCESS		read-only
		STATUS		mandatory
		DESCRIPTION
			"Channel number of last outbound call."
		::= { cdx6500SPSTXDLCMX25StnEntry 74 }

	cdx6500xdlcmx25OutStatus OBJECT-TYPE
		SYNTAX		DisplayString
		ACCESS		read-only
		STATUS		mandatory
		DESCRIPTION
			"Success: Message has been through the network successfully.

			Process OK, call passed to ROUTE: Inbound call has been processed and
			passed to Route and is being processed.

			Failed processing, call cleared: Inbound message was processed, but
			failed for some reason, and the call has been cleared."
		::= { cdx6500SPSTXDLCMX25StnEntry 75 }

	cdx6500xdlcmx25LOCBPCalledAddr OBJECT-TYPE
		SYNTAX		DisplayString
		ACCESS		read-only
		STATUS		mandatory
		DESCRIPTION
			"Last outbound call before processing: the X.25 address that was
			called."
		::= { cdx6500SPSTXDLCMX25StnEntry 76 }

	cdx6500xdlcmx25LOCBPCallingAddr OBJECT-TYPE
		SYNTAX		DisplayString
		ACCESS		read-only
		STATUS		mandatory
		DESCRIPTION
			"Last outbound call before processing: the X.25 address that initiated
			the call."
		::= { cdx6500SPSTXDLCMX25StnEntry 77 }

	cdx6500xdlcmx25LOCBPFacilities OBJECT-TYPE
		SYNTAX		DisplayString
		ACCESS		read-only
		STATUS		mandatory
		DESCRIPTION
			"Last outbound call before processing: the facilities that were
			requested in the most recent call request packet."
		::= { cdx6500SPSTXDLCMX25StnEntry 78 }

	cdx6500xdlcmx25LOCBPCUD OBJECT-TYPE
		SYNTAX		DisplayString
		ACCESS		read-only
		STATUS		mandatory
		DESCRIPTION
			"Last outbound call before processing: Call User Data contains end-user
			or routing information specific to the network."
		::= { cdx6500SPSTXDLCMX25StnEntry 79 }

	cdx6500xdlcmx25LOCAPCalledAddr OBJECT-TYPE
		SYNTAX		DisplayString
		ACCESS		read-only
		STATUS		mandatory
		DESCRIPTION
			"Last outbound call after processing: the X.25 address that was
			called."
		::= { cdx6500SPSTXDLCMX25StnEntry 80 }

	cdx6500xdlcmx25LOCAPCallingAddr OBJECT-TYPE
		SYNTAX		DisplayString
		ACCESS		read-only
		STATUS		mandatory
		DESCRIPTION
			"Last outbound call after processing: the X.25 address that initiated
			the call."
		::= { cdx6500SPSTXDLCMX25StnEntry 81 }

	cdx6500xdlcmx25LOCAPFacilities OBJECT-TYPE
		SYNTAX		DisplayString
		ACCESS		read-only
		STATUS		mandatory
		DESCRIPTION
			"Last outbound call after processing: the facilities that were
			requested in the most recent call request packet."
		::= { cdx6500SPSTXDLCMX25StnEntry 82 }

	cdx6500xdlcmx25LOCAPCUD OBJECT-TYPE
		SYNTAX		DisplayString
		ACCESS		read-only
		STATUS		mandatory
		DESCRIPTION
			"Last outbound call after processing: Call User Data contains end-user
			or routing information specific to the network."
		::= { cdx6500SPSTXDLCMX25StnEntry 83 }





	-- The XDLC Station Controls Table
	-- This table contains Control paramaters 
	-- for the XDLC Station table.
			
	cdx6500ContXDLCStationTable OBJECT-TYPE
		SYNTAX		SEQUENCE OF Cdx6500ContXDLCStationEntry
		ACCESS		not-accessible
		STATUS		mandatory
		DESCRIPTION
			"All of the control parameters relevant
			 to the XDLC Station table."
		::= { cdx6500ContXDLC 1 }
			
	cdx6500ContXDLCStationEntry OBJECT-TYPE
		SYNTAX		Cdx6500ContXDLCStationEntry
		ACCESS		not-accessible
		STATUS		mandatory
		DESCRIPTION
			"A row of XDLC Station Control parameters."
		INDEX	{ cdx6500xdlcsContPortNum, cdx6500xdlcsContStationNum }
		::= { cdx6500ContXDLCStationTable 1 }
			
	Cdx6500ContXDLCStationEntry ::=
		SEQUENCE {
			cdx6500xdlcsContPortNum
				INTEGER,
			cdx6500xdlcsContStationNum
				INTEGER,
			cdx6500xdlcsContBootStation
				INTEGER,
			cdx6500xdlcsContDisableStation
				INTEGER,
			cdx6500xdlcsContEnableStation
				INTEGER,
			cdx6500xdlcsContResetStnStats
				INTEGER
			}
			
	cdx6500xdlcsContPortNum OBJECT-TYPE
		SYNTAX		INTEGER (1..54)
		ACCESS		not-accessible
		STATUS		mandatory
		DESCRIPTION
			"XDLC Port Number"
		::= { cdx6500ContXDLCStationEntry 1 }
			
	cdx6500xdlcsContStationNum OBJECT-TYPE
		SYNTAX		INTEGER (1..4)
		ACCESS		not-accessible
		STATUS		mandatory
		DESCRIPTION
			"XDLC Station Number"
		::= { cdx6500ContXDLCStationEntry 2 }
			
	cdx6500xdlcsContBootStation OBJECT-TYPE
		SYNTAX		INTEGER {
					boot(1),
					noBoot(2)
					}
		ACCESS		write-only
		STATUS		mandatory
		DESCRIPTION
			"Boots the specified XDLC station.

			1 - Boot Station
			2 - Do not boot Station"
		DEFVAL { noBoot }
		::= { cdx6500ContXDLCStationEntry 3 }
			
	cdx6500xdlcsContDisableStation OBJECT-TYPE
		SYNTAX		INTEGER {
					disable(1),
					noDisable(2)
					}
		ACCESS		write-only
		STATUS		mandatory
		DESCRIPTION
			"Disables the specified XDLC station.

			1 - Disable Station
			2 - Do not disable Station"
		DEFVAL { noDisable }
		::= { cdx6500ContXDLCStationEntry 4 }
			
	cdx6500xdlcsContEnableStation OBJECT-TYPE
		SYNTAX		INTEGER {
					enable(1),
					noEnable(2)
					}
		ACCESS		write-only
		STATUS		mandatory
		DESCRIPTION
			"Enables the specified XDLC station.

			1 - Enable Station
			2 - Not not enable Station"
		DEFVAL { noEnable }
		::= { cdx6500ContXDLCStationEntry 5 }
			
	cdx6500xdlcsContResetStnStats OBJECT-TYPE
		SYNTAX		INTEGER {
					reset(1),
					noReset(2)
					}
		ACCESS		write-only
		STATUS		mandatory
		DESCRIPTION
			"Resets statistics for the specified XDLC station

			1 - Reset Station Statistics
			2 - Do not reset Station Statistics"
		DEFVAL { noReset }
		::= { cdx6500ContXDLCStationEntry 6 }

END
