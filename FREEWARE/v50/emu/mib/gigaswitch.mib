-- The GIGAswitch MIB version gigaversion1
-- Mon Jun  6 17:29:43 EDT 1994


	GIGASWITCH-MIB DEFINITIONS ::= BEGIN
	IMPORTS
		enterprises, IpAddress, experimental, Counter
			FROM RFC1155-SMI
		OBJECT-TYPE
			FROM RFC-1212
		DisplayString, transmission
			FROM RFC1213-MIB;

	dec             OBJECT IDENTIFIER ::= { enterprises 36 }
	ema             OBJECT IDENTIFIER ::= { dec 2 }

	sysobjid	OBJECT IDENTIFIER ::= { ema 15 }
	bridges		OBJECT IDENTIFIER ::= { sysobjid 3 }
	gigaswitch	OBJECT IDENTIFIER ::= { bridges 3 }

	minimumGIGAswitchMIBVersionSupported OBJECT-TYPE
		SYNTAX	INTEGER
		ACCESS	read-only
		STATUS	mandatory
		DESCRIPTION
			"
			When new GIGAswitch MIBs are released to the public,
			they will be given new version numbers.  The
			implementation strategy allows multiple versions to be
			supported simultaneously.  MIB versions greater than or
			equal to this version are still supported.
			"
	::= { gigaswitch 1 }

	maximumGIGAswitchMIBVersionSupported OBJECT-TYPE
		SYNTAX	INTEGER
		ACCESS	read-only
		STATUS	mandatory
		DESCRIPTION
			"
			When new GIGAswitch MIBs are released to the public,
			they will be given new version numbers.  The
			implementation strategy allows multiple versions to be
			supported simultaneously.  MIB versions less than or
			equal to this version are still supported.  A management
			station may load a MIB which is not supported until
			the GIGAswitch software is updated.
			"
	::= { gigaswitch 2 }

	gigaversion1 OBJECT IDENTIFIER ::= { gigaswitch 3 }







	gigaBox	OBJECT IDENTIFIER ::= { gigaversion1 1 }

	gigaBridge	OBJECT IDENTIFIER ::= { gigaversion1 2 }

	gigaUpgradeSoftware OBJECT IDENTIFIER ::= { gigaversion1 3 }

	gigaIP OBJECT IDENTIFIER ::= { gigaversion1 4 }




	serviceClassAssignments OBJECT IDENTIFIER ::= { gigaBridge 5 }










    filterByReferencedExpression OBJECT IDENTIFIER ::= { gigaBridge 1 }

    ebrNportMatrixNameTable OBJECT-TYPE
	SYNTAX	SEQUENCE OF EbrNportMatrixNameEntry
	ACCESS	not-accessible
	STATUS	mandatory
	DESCRIPTION "This table allows filter matrices to be succinctly
		specified and named.  These matrices may later be used
		and combined in filter specifications."
	::= { filterByReferencedExpression 1 }

    ebrNportMatrixNameEntry OBJECT-TYPE
	SYNTAX	EbrNportMatrixNameEntry
	ACCESS	not-accessible
	STATUS	mandatory
	DESCRIPTION "A particular named filter matrix."
	INDEX { ebrNportMatrixName }
	::= { ebrNportMatrixNameTable 1 }

    EbrNportMatrixNameEntry ::=
	SEQUENCE {
		ebrNportMatrixName	DisplayString,
		ebrNportMatrixValue	DisplayString,
		ebrNportMatrixStatus	INTEGER,
		ebrNportMatrixFppnValue	DisplayString
	}

    ebrNportMatrixName OBJECT-TYPE
	SYNTAX	DisplayString (SIZE (32))
	ACCESS	read-only
	STATUS	mandatory
	DESCRIPTION "This name for a filter matrix is whatever the user likes,
		as long as it is a unique filter matrix name."
	::= { ebrNportMatrixNameEntry 1 }

    ebrNportMatrixValue OBJECT-TYPE
	SYNTAX	DisplayString (SIZE (32))
	ACCESS	read-write
	STATUS	mandatory
	DESCRIPTION
		"A matrix is expressed using a shorthand that says what
		input ports can talk to what output ports.

		An examples of a specification is:
			11:1; 1:3-5; 2:0,3; 4-7,9:4-7,9; 10:

		Semicolons separate expressions.  Within each expression,
		the colon has a left hand side and a right hand side.  Bridge
		ports on the left hand side can send packets to bridge ports
		on the right hand side.  Commas separate items in a list of
		bridge ports.  Hyphens are short-hand for specifying a range
		of numbers.  If there is no right hand side, the bridge ports
		on the left cannot send packets to any bridge port (unless the
		matrix is combined with some some other matrix in a filter
		specification, or unless the filter is overridden).

		Bridge port numbers are specified in decimal.

		A matrix will read back in a form equivalent to the form
		written.  It may not read back exactly as written.

		No single matrix defines whether a packet arriving on a port
		is forwarded to its destination.  Various destination address,
		source address, protocol, and default filtering specifications
		are combined to determine whether the packet is forwarded.

		If the ebrNportMatrixValue is changed, all filters using it are
		immediately updated."
	::= { ebrNportMatrixNameEntry 2 }

    ebrNportMatrixStatus OBJECT-TYPE
	SYNTAX INTEGER {
		invalid(1),
		permanent(2)
	}
	ACCESS	read-write
	STATUS	mandatory
	DESCRIPTION "Assigning the value invalid will result in an error
		while the matrix is still reference by some filter.

		All matrices are permanent; it is their usage which may or may
		not be temporary."
	::= { ebrNportMatrixNameEntry 3 }

    ebrNportMatrixFppnValue OBJECT-TYPE
	SYNTAX	DisplayString (SIZE (32))
	ACCESS	read-write
	STATUS	mandatory
	DESCRIPTION
		"A matrix is expressed using a shorthand that says what
		input ports can talk to what output ports.

                An examples of a specification is:
                        1.1,2.1-14.2:1.1-14.2; 2.2:5.3,6.4; 10.3:;

                Semicolons separate expressions.  Within each expression,
                the colon has a left hand side and a right hand side.  Front
                panel ports on the left hand side can send packets to front
                panel ports on the right hand side.  Commas separate items in
                a list of front panel ports.  Hyphens are short-hand for
                specifying a range of numbers.  If there is no right hand side,
                the front panel ports on the left cannot send packets to any
                front panel port (unless the matrix is combined with some some
                other matrix in a filter specification, or unless the filter is
                overridden).

                Front panel port numbers are of the form (slot.connector),
		where slot is the slot number the module is plugged into,
		and connector is the connector number specified on the
		front of the card.

		A matrix will read back in a form equivalent to the form
		written.  It may not read back exactly as written.

		No single matrix defines whether a packet arriving on a port
		is forwarded to its destination.  Various destination address,
		source address, protocol, and default filtering specifications
		are combined to determine whether the packet is forwarded.

		If the ebrNportMatrixFppnValue is changed, all filters using 
		it are immediately updated.

                Managers may not specify both ebrNportMatrixValue and
                ebrNportMatrixFppnValue at the same time to set an entry
                in this table."
	::= { ebrNportMatrixNameEntry 4 }

    ebrNportSapNameTable OBJECT-TYPE
	SYNTAX	SEQUENCE OF EbrNportSapNameEntry
	ACCESS	not-accessible
	STATUS	mandatory
	DESCRIPTION "The filters specified by SAP protocol."
	::= { filterByReferencedExpression 2 }

    ebrNportSapNameEntry OBJECT-TYPE
	SYNTAX	EbrNportSapNameEntry
	ACCESS	not-accessible
	STATUS	mandatory
	DESCRIPTION "A portion of a particular filter for a particular SAP
		protocol."
	INDEX { ebrNportSapName }
	::= { ebrNportSapNameTable 1 }

    EbrNportSapNameEntry ::=
	SEQUENCE {
		ebrNportSapName		DisplayString,
		ebrNportSapNameSap	OCTET STRING,
		ebrNportSapMatrixName	DisplayString,
		ebrNportSapNameDisp	INTEGER,
		ebrNportSapNameStatus	INTEGER
	}

    ebrNportSapName OBJECT-TYPE
	SYNTAX	DisplayString (SIZE (32))
	ACCESS	read-only
	STATUS	mandatory
	DESCRIPTION "This name for a portion of a filter is whatever the user
		likes, as long as it is a unique ebrNportSapName.

		The combination of ebrNportSapNameSap and ebrNportSapMatrixName
		is unique within this table.  Insertions of new names for 
		pre-existing combinations will be denied.
		
		ebrNportSapName is present and is the index to give a mnemonic
		handle on the combination of SAP and matrix for purposes of
		discussion and of access through the network management station
		user interface.  SAPs, for example, are often just meaningless
		numbers unless laborious steps are taken to interpret them.
		"
	::= { ebrNportSapNameEntry 1 }

    ebrNportSapNameSap OBJECT-TYPE
	SYNTAX	OCTET STRING (SIZE (1))
	ACCESS	read-write
	STATUS	mandatory
	DESCRIPTION
		"The one-byte SAP.

		Changes to ebrNportSapProtoTable for this SAP are denied while
		filtering of the SAP is specified by reference to a named
		matrix using this table."
	::= { ebrNportSapNameEntry 2 }

    ebrNportSapMatrixName OBJECT-TYPE
	SYNTAX	DisplayString (SIZE (32))
	ACCESS	read-write
	STATUS	mandatory
	DESCRIPTION "A ebrNportMatrixName.  Multiple matrices for the same SAP
		are combined using an elementwise-OR operator."
	::= { ebrNportSapNameEntry 3 }

    ebrNportSapNameDisp OBJECT-TYPE
	SYNTAX	INTEGER	{

                           filter(1),
			   alwaysFilter(2),
                           alwaysForward(3)
		}
	ACCESS	read-write
	STATUS	mandatory
	DESCRIPTION
		"

                  filter(1) : The filtering for this SAP is specified by the
			filter matrix.

		  alwaysFilter(2) : Frames of this SAP (protocol) are
			filtered regardless of any other alwaysForward
			dispositions based on the frame's address.
			The filtering information is specified by the
			filter matrix.

                  alwaysForward(3) : Frames for this SAP (protocol) are
			sent to ports specified in the filter matrix
			regardless of any address filter with a
			disposition of filter. The alwaysForward disposition
			also overrides a forwarding disposition of filter
			in the default filter matrix object.

			Filters with a disposition of alwaysFilter are never
			superceded.

		Setting this object will side-effect the
		ebrNportSapFilterCharacteristicsTable entry for this SAP.  It
		is here to group information for window-based forms.  Setting
		this object will also side-effect other entries in this table
		with the same SAP value.
		"
	::= { ebrNportSapNameEntry 4 }

    ebrNportSapNameStatus OBJECT-TYPE
	SYNTAX	INTEGER {

			invalid(1),
			permanent(2)
		}
	ACCESS	read-write
	STATUS	mandatory
	DESCRIPTION
		"

		This object specifies the permanence of the associated filter
		matrix, and also provides a means to delete a filter matrix.

                Writing invalid(1) to the object removes the filter.

                Writing permanent(2) value to the object indicates the filter is
                preserved across a bridge reset.
		"
	::= { ebrNportSapNameEntry 5 }

    ebrNportSnapNameTable OBJECT-TYPE
	SYNTAX	SEQUENCE OF EbrNportSnapNameEntry
	ACCESS	not-accessible
	STATUS	mandatory
	DESCRIPTION "The filters specified by Protocol ID for the SNAP SAP."
	::= { filterByReferencedExpression 3 }

    ebrNportSnapNameEntry OBJECT-TYPE
	SYNTAX	EbrNportSnapNameEntry
	ACCESS	not-accessible
	STATUS	mandatory
	DESCRIPTION "A portion of a particular filter for a particular
		Protocol ID."
	INDEX { ebrNportSnapName }
	::= { ebrNportSnapNameTable 1 }

    EbrNportSnapNameEntry ::=
	SEQUENCE {
		ebrNportSnapName	DisplayString,
		ebrNportSnapNameSnap	OCTET STRING,
		ebrNportSnapMatrixName	DisplayString,
		ebrNportSnapNameDisp	INTEGER,
		ebrNportSnapNameStatus	INTEGER
	}

    ebrNportSnapName OBJECT-TYPE
	SYNTAX	DisplayString (SIZE (32))
	ACCESS	read-only
	STATUS	mandatory
	DESCRIPTION "This name for a portion of a filter is whatever the user
		likes, as long as it is a unique ebrNportSnapName.

		The combination of ebrNportSnapNameSnap and
		ebrNportSnapMatrixName is unique within this table.  Insertions
		of new names for pre-existing combinations will be denied.

		ebrNportSnapName is present and is the index to give a mnemonic
		handle on the combination of protocol and matrix for purposes
		of discussion and of access through the network management
		station user interface.  Protocol IDs, for example, are often
		just meaningless numbers unless laborious steps are taken to
		interpret them.
		"
	::= { ebrNportSnapNameEntry 1 }

    ebrNportSnapNameSnap OBJECT-TYPE
	SYNTAX	OCTET STRING (SIZE (5))
	ACCESS	read-write
	STATUS	mandatory
	DESCRIPTION
		"The five-byte PID.

		Changes to ebrNportSnapProtoTable for this protocol are denied
		while filtering of the protocol is specified by reference to a
		named matrix using this table."
	::= { ebrNportSnapNameEntry 2 }

    ebrNportSnapMatrixName OBJECT-TYPE
	SYNTAX	DisplayString (SIZE (32))
	ACCESS	read-write
	STATUS	mandatory
	DESCRIPTION "A ebrNportMatrixName.  Multiple matrices for the same PID
		are combined using an elementwise-OR operator."
	::= { ebrNportSnapNameEntry 3 }

    ebrNportSnapNameDisp OBJECT-TYPE
	SYNTAX	INTEGER {

                           filter(1),
			   alwaysFilter(2),
                           alwaysForward(3)
		}
	ACCESS	read-write
	STATUS	mandatory
	DESCRIPTION
		"

                  filter(1) : The filtering for this Protocol ID
                      is specified by the filter matrix.

		  alwaysFilter(2) : Frames of this Protocol ID are
			filtered regardless of any other alwaysForward
			dispositions based on the frame's address.
			The filtering information is specified by the
			filter matrix.

                  alwaysForward(3) : Frames for this Protocol ID are
			sent to ports specified in the filter matrix
			regardless of any address filter with a
			disposition of filter. The alwaysForward disposition
			also overrides a forwarding disposition of filter
			in the default filter matrix object.

			Filters with a disposition of alwaysFilter are never
			superceded.

		Setting this object will side-effect the
		ebrNportSnapFilterCharacteristicsTable entry for this protocol.
		It is here to group information for window-based forms.  Setting
		this object will also side-effect other entries in this table
		with the same protocol value.
		"
	::= { ebrNportSnapNameEntry 4 }
	
    ebrNportSnapNameStatus OBJECT-TYPE
	SYNTAX	INTEGER {

			invalid(1),
			permanent(2)
		}
	ACCESS	read-write
	STATUS	mandatory
	DESCRIPTION
		"

		This object specifies the permanence of the associated filter
		matrix, and also provides a means to delete a filter matrix.

                Writing invalid(1) to the object removes the filter.

                Writing permanent(2) value to the object indicates the filter is
                preserved across a bridge reset.
		"
	::= { ebrNportSnapNameEntry 5 }

    ebrNportDANameTable OBJECT-TYPE
	SYNTAX	SEQUENCE OF EbrNportDANameEntry
	ACCESS	not-accessible
	STATUS	mandatory
	DESCRIPTION "The filters specified by destination address."
	::= { filterByReferencedExpression 4 }

    ebrNportDANameEntry OBJECT-TYPE
	SYNTAX	EbrNportDANameEntry
	ACCESS	not-accessible
	STATUS	mandatory
	DESCRIPTION "A portion of a particular filter for a particular
		destination address."
	INDEX { ebrNportDAName }
	::= { ebrNportDANameTable 1 }

    EbrNportDANameEntry ::=
	SEQUENCE {
		ebrNportDAName		DisplayString,
		ebrNportDANameDA	OCTET STRING,
		ebrNportDAMatrixName	DisplayString,
		ebrNportDANameDisp	INTEGER,
		ebrNportDANameStatus	INTEGER
	}

    ebrNportDAName OBJECT-TYPE
	SYNTAX	DisplayString (SIZE (32))
	ACCESS	read-only
	STATUS	mandatory
	DESCRIPTION "
		This name for a portion of a filter is whatever the user likes,
		as long as it is a unique ebrNportDAName.

		The combination of ebrNportDANameDA and ebrNportDAMatrixName
		is unique within this table.  Insertions of new names for
		pre-existing combinations will be denied.

		ebrNportDAName is present and is the index to give a mnemonic
		handle on the combination of address and matrix for purposes of
		discussion and of access through the network management station
		user interface.  Addresses, for example, are often just
		meaningless numbers unless laborious steps are taken to
		interpret them.
		"
	::= { ebrNportDANameEntry 1 }

    ebrNportDANameDA OBJECT-TYPE
	SYNTAX	OCTET STRING (SIZE (6))
	ACCESS	read-write
	STATUS	mandatory
	DESCRIPTION "The six-byte destination address.

		Changes to ebrNportStaticDATable for this address are denied
		while filtering of the address is specified by reference to a
		named matrix using this table."
	::= { ebrNportDANameEntry 2 }

    ebrNportDAMatrixName OBJECT-TYPE
	SYNTAX	DisplayString (SIZE (32))
	ACCESS	read-write
	STATUS	mandatory
	DESCRIPTION "A ebrNportMatrixName.  Multiple matrices for the same
		address are combined using an elementwise-OR operator."
	::= { ebrNportDANameEntry 3 }

    ebrNportDANameDisp OBJECT-TYPE
	SYNTAX	INTEGER {

			filter(1),
			alwaysFilter(2),
			alwaysForward(3)
		}
	ACCESS	read-write
	STATUS	mandatory
	DESCRIPTION
		"

                  filter(1) : The filtering for this address is specified by
			the filter matrix.

		  alwaysFilter(2) : Frames destined to address are filtered
			regardless of any other alwaysForward dispositions
			based on the frame's source address or protocol type.
			The filtering information is specified by the filter
			matrix.

                  alwaysForward(3) : Frames destined to address are always
			forwarded to ebrNportPortNum if specified.
			The filter matrix is used to specify ports to
			which frames may be sent. In both cases, this
			disposition overrides filters based on the frame's
			source address or protocol type, unless either of those
			filters has an alwaysFilter disposition.

		Setting this object will side effect the
		ebrNportStaticDAFilterCharacteristicsTable entry for this
		address.  It is here to group information for window-based
		forms.  Setting this object will also side-effect other
		entries in this table with the same address.
		"
	::= { ebrNportDANameEntry 4 }
	
    ebrNportDANameStatus OBJECT-TYPE
	SYNTAX	INTEGER {

			other(1),
			invalid(2),
			permanent(3),
			deleteOnReset(4),
			deleteOnTimeout(5)
		}
	ACCESS	read-write
	STATUS	mandatory
	DESCRIPTION
		"

		other(1) - This entry is currently in use, but the 
			conditions under which it will remain so are different
			from each of the following values.  Like other uses
			of 'other' in MIBs, this value may not be assigned to
			the object.

		invalid(2) - Writing this value to the object removes the entry

		permanent(3) - Writing this value to the object indicates that
			the entry is preserved across a bridge reset.

		deleteOnReset(4) - Writing this value removes the permanent
			entry characteristic.  The entry is deleted upon the
			next bridge reset (SCP or GIGAswitch failure).

			Writing deleteOnReset is not supported.  SNMP does not
			currently model viewing the non-volatile and volatile
			data structures independently, which can lead to
			unexpectedly having no filter if a reset occurs while
			temporarily trying a change to an existing filter.
			Writes of this value will result in a bad value return
			status.  It is present for consistency with the Bridge
			MIB (RFC 1286), which describes address filters.

		deleteOnTimeout(5) - Writing this value removes the permanent
			entry characteristic.  Since the timers used for aging
			information within the bridge are hidden from the user,
			the change may in fact take place immediately.

			Writing deleteOnTimeout is not supported.  SNMP does not
			currently model viewing the non-volatile and volatile
			data structures independently, which can lead to
			unexpectedly having no filter if a reset occurs while
			temporarily trying a change to an existing filter.
			Writes of this value will result in a bad value return
			status.  It is present for consistency with the Bridge
			MIB (RFC 1286), which describes address filters.
		"
	::= { ebrNportDANameEntry 5 }

    ebrNportSANameTable OBJECT-TYPE
	SYNTAX	SEQUENCE OF EbrNportSANameEntry
	ACCESS	not-accessible
	STATUS	mandatory
	DESCRIPTION "The filters specified by source address."
	::= { filterByReferencedExpression 5 }

    ebrNportSANameEntry OBJECT-TYPE
	SYNTAX	EbrNportSANameEntry
	ACCESS	not-accessible
	STATUS	mandatory
	DESCRIPTION "A portion of a particular filter for a particular source
		address."
	INDEX { ebrNportSAName }
	::= { ebrNportSANameTable 1 }

    EbrNportSANameEntry ::=
	SEQUENCE {
		ebrNportSAName		DisplayString,
		ebrNportSANameSA	OCTET STRING,
		ebrNportSAMatrixName	DisplayString,
		ebrNportSANameDisp	INTEGER,
		ebrNportSANameStatus	INTEGER
	}

    ebrNportSAName OBJECT-TYPE
	SYNTAX	DisplayString (SIZE (32))
	ACCESS	read-only
	STATUS	mandatory
	DESCRIPTION "
		This name for a portion of a filter is whatever the user
		likes, as long as it is a unique ebrNportSAName.

		The combination of ebrNportSANameSA and ebrNportSAMatrixName
		is unique within this table.  Insertions of new names for
		pre-existing combinations will be denied.

		ebrNportSAName is present and is the index to give a mnemonic
		handle on the combination of address and matrix for purposes of
		discussion and of access through the network management station
		user interface.  Addresses, for example, are often just
		meaningless numbers unless laborious steps are taken to
		interpret them.
		"
	::= { ebrNportSANameEntry 1 }

    ebrNportSANameSA OBJECT-TYPE
	SYNTAX	OCTET STRING (SIZE (6))
	ACCESS	read-write
	STATUS	mandatory
	DESCRIPTION
		"The six-byte source address.

		Changes to ebrNportStaticSATable for this address are denied
		while filtering of the address is specified by reference to a
		named matrix using this table."
	::= { ebrNportSANameEntry 2 }

    ebrNportSAMatrixName OBJECT-TYPE
	SYNTAX	DisplayString (SIZE (32))
	ACCESS	read-write
	STATUS	mandatory
	DESCRIPTION "A ebrNportMatrixName.  Multiple matrices for the same
		address are combined using an elementwise-OR operator."
	::= { ebrNportSANameEntry 3 }

    ebrNportSANameDisp OBJECT-TYPE
	SYNTAX	INTEGER {

                  portMask(1),
		  alwaysFilter(2),
                  alwaysForward(3),
		  lockdown(4),
		  lockdownportmask(5),
		  filter(6)
		}
	ACCESS	read-write
	STATUS	mandatory
	DESCRIPTION
		"This object specifies how to interpret the ebrNportPortNum and
		the ebrNportSAMatrixName objects.


                  portMask(1) : The static filtering for this address
                      is specified by the filter matrix.

		  alwaysFilter(2) : Frames sourced from this address are
			filtered regardless of any other alwaysForward
			dispositions based on the frame's destination address
			or protocol type. The static filtering information is
			specified by the filter matrix.

                  alwaysForward(3) : Frames sourced from this address are
			sent to ports specified in the filter matrix
			regardless of any DA or protocol filter with a
			disposition of filter. The alwaysForward disposition
			also overrides a forwarding disposition of filter
			in the default filter matrix object.

			Filters with a disposition of alwaysFilter are never
			superceded.

		  lockdown (4) : Frames sourced from this address
			are ONLY forwarded if received on the same port as
			ebrNportPortNum.

		  lockdownportmask (5) : Frames sourced from this address
			are ONLY forwarded if received on the same port as
			ebrNportPortNum AND if the frame is destined to a
			permitted port as specified by the filter matrix.

                  filter(6) : The static filtering for this address
                      is specified by the filter matrix.  portMask(1) is
		      the different name with the same effect.

		Setting this object will side effect the
		ebrNportStaticSAFilterCharacteristicsTable entry for this
		address.  It is here to group information for window-based
		forms.  Setting this object will also side-effect other
		entries in this table with the same address.
		"
	::= { ebrNportSANameEntry 4 }

    ebrNportSANameStatus OBJECT-TYPE
	SYNTAX	INTEGER {

			other(1),
			invalid(2),
			permanent(3),
			deleteOnReset(4),
			deleteOnTimeout(5)
		}
	ACCESS	read-write
	STATUS	mandatory
	DESCRIPTION
		"

		other(1) - This entry is currently in use, but the 
			conditions under which it will remain so are different
			from each of the following values.  Like other uses
			of 'other' in MIBs, this value may not be assigned to
			the object.

		invalid(2) - Writing this value to the object removes the entry

		permanent(3) - Writing this value to the object indicates that
			the entry is preserved across a bridge reset.

		deleteOnReset(4) - Writing this value removes the permanent
			entry characteristic.  The entry is deleted upon the
			next bridge reset (SCP or GIGAswitch failure).

			Writing deleteOnReset is not supported.  SNMP does not
			currently model viewing the non-volatile and volatile
			data structures independently, which can lead to
			unexpectedly having no filter if a reset occurs while
			temporarily trying a change to an existing filter.
			Writes of this value will result in a bad value return
			status.  It is present for consistency with the Bridge
			MIB (RFC 1286), which describes address filters.

		deleteOnTimeout(5) - Writing this value removes the permanent
			entry characteristic.  Since the timers used for aging
			information within the bridge are hidden from the user,
			the change may in fact take place immediately.

			Writing deleteOnTimeout is not supported.  SNMP does not
			currently model viewing the non-volatile and volatile
			data structures independently, which can lead to
			unexpectedly having no filter if a reset occurs while
			temporarily trying a change to an existing filter.
			Writes of this value will result in a bad value return
			status.  It is present for consistency with the Bridge
			MIB (RFC 1286), which describes address filters.
		"
	::= { ebrNportSANameEntry 5 }

    ebrNportMatrixNameRowTable OBJECT-TYPE
	SYNTAX	SEQUENCE OF EbrNportMatrixNameRowEntry
	ACCESS	not-accessible
	STATUS	mandatory
	DESCRIPTION "
		This table is another view of ebrNportMatrixNameTable.  The
		tables side-effect one another.

		Users or programs can choose whichever matrix specification
		language they feel more comfortable with.  This table also
		side-steps issues of the worst-case ascii representation length
		on the part of either ebrNportMatrixNameTable or the management
		station interface.
		"
	::= { filterByReferencedExpression 8 }

    ebrNportMatrixNameRowEntry OBJECT-TYPE
	SYNTAX	EbrNportMatrixNameRowEntry
	ACCESS	not-accessible
	STATUS	mandatory
	DESCRIPTION "A particular row of a particular named filter matrix."
	INDEX { ebrNportmatrixName, ebrNportMatrixReceivePort }
	::= { ebrNportMatrixNameRowTable 1 }

    EbrNportMatrixNameRowEntry ::=
	SEQUENCE {
		ebrNportmatrixName		DisplayString,
		ebrNportMatrixReceivePort	INTEGER,
		ebrNportMatrixAllowedToGoTo	OCTET STRING,
		ebrNportMatrixNameRowStatus	INTEGER
	}

    ebrNportmatrixName OBJECT-TYPE
	SYNTAX	DisplayString (SIZE (32))
	ACCESS	read-only
	STATUS	mandatory
	DESCRIPTION "
		This name for a filter matrix is whatever the user likes,
		as long as it is a unique filter matrix name.

		Same as ebrNportMatrixName.
		"
	::= { ebrNportMatrixNameRowEntry 1 }

    ebrNportMatrixReceivePort OBJECT-TYPE
	SYNTAX	INTEGER
	ACCESS	read-only
	STATUS	mandatory
	DESCRIPTION
		"A bridge port number.  Zero is treated as in other tables,
		and is short-hand for all rows not previously mentioned."
	::= { ebrNportMatrixNameRowEntry 2 }

    ebrNportMatrixAllowedToGoTo OBJECT-TYPE
	SYNTAX OCTET STRING (SIZE (5))
	ACCESS	read-write
	STATUS	mandatory
	DESCRIPTION
		"Just like all the other GoTos.  The set of ports to which
		frames received from a specific port are allowed to be
		forwarded.

		Each octet of this object specifies a set of eight ports,
                with the first octet specifying ports 1 through 8,
                the second octet specifying port 9 through 16 etc.
                Within each octet, the most significant bit represents
                the lowest numbered port, and the least significant
                bit represents the highest numbered port.  If a
                bit has a value of '1', then the corresponding port
                is included in the set of ports; the port is not
                included if its bit has a value of '0'.

		If the ebrNportMatrixAllowedToGoTo is changed, all filters
		using it are immediately updated."
	::= { ebrNportMatrixNameRowEntry 3 }

     ebrNportMatrixNameRowStatus OBJECT-TYPE
	SYNTAX	INTEGER {
			invalid(1),
			permanent(2)
		}
	ACCESS	read-write
	STATUS	mandatory
	DESCRIPTION "
		Assigning the value invalid will delete the row of the matrix.
		Attempting to delete the last ebrNportmatrixName entry for a
		matrix will result in an error while the matrix is still
		reference by some filter.

		All matrices are permanent; it is their usage which may or may
		not be temporary.
		"
	::= { ebrNportMatrixNameRowEntry 4 }

    ebrNportMatrixFppnRowTable OBJECT-TYPE
	SYNTAX	SEQUENCE OF EbrNportMatrixFppnRowEntry
	ACCESS	not-accessible
	STATUS	mandatory
	DESCRIPTION "
		This table is yet another view of ebrNportMatrixNameTable.  The
		tables side-effect one another.

		Users or programs can choose whichever matrix specification
		language they feel more comfortable with.  This table also
		side-steps issues of the worst-case ascii representation length
		on the part of either ebrNportMatrixNameTable or the management
		station interface.
		"
	::= { filterByReferencedExpression 11 }

    ebrNportMatrixFppnRowEntry OBJECT-TYPE
	SYNTAX	EbrNportMatrixFppnRowEntry
	ACCESS	not-accessible
	STATUS	mandatory
	DESCRIPTION "A particular row of a particular named filter matrix."
	INDEX { ebrNportmatrixname, ebrNportMatrixFppnReceivePort }
	::= { ebrNportMatrixFppnRowTable 1 }

    EbrNportMatrixFppnRowEntry ::=
	SEQUENCE {
		ebrNportmatrixname		DisplayString,
		ebrNportMatrixFppnReceivePort	DisplayString,
		ebrNportMatrixFppnAllowedToGoTo	OCTET STRING,
		ebrNportMatrixFppnRowStatus	INTEGER
	}

    ebrNportmatrixname OBJECT-TYPE
	SYNTAX	DisplayString (SIZE (32))
	ACCESS	read-only
	STATUS	mandatory
	DESCRIPTION "
		This name for a filter matrix is whatever the user likes,
		as long as it is a unique filter matrix name.

		Same as ebrNportMatrixName.
		"
	::= { ebrNportMatrixFppnRowEntry 1 }

    ebrNportMatrixFppnReceivePort OBJECT-TYPE
	SYNTAX	DisplayString
	ACCESS	read-only
	STATUS	mandatory
	DESCRIPTION "

                Front panel port numbers are of the form (slot.connector),
		where slot is the slot number the module is plugged into,
		and connector is the connector number specified on the
		front of the card.

		To avoid the syntactic ambiguity, the slot number must take
		two characters.  For example, front panel port number 3.1 
		must be typed by 03.1.   0.0 is treated as in other tables, 
		and is short-hand for all rows not previously mentioned."
	::= { ebrNportMatrixFppnRowEntry 2 }

    ebrNportMatrixFppnAllowedToGoTo OBJECT-TYPE
	SYNTAX OCTET STRING (SIZE (5))
	ACCESS	read-write
	STATUS	mandatory
	DESCRIPTION
		"Just like all the other GoTos.  The set of ports to which
		frames received from a specific port are allowed to be
		forwarded.

		Each octet of this object specifies a set of eight ports,
                with the first octet specifying ports 1 through 8,
                the second octet specifying port 9 through 16 etc.
                Within each octet, the most significant bit represents
                the lowest numbered port, and the least significant
                bit represents the highest numbered port.  If a
                bit has a value of '1', then the corresponding port
                is included in the set of ports; the port is not
                included if its bit has a value of '0'.

		If the ebrNportMatrixFppnAllowedToGoTo is changed, all filters
		using it are immediately updated."
	::= { ebrNportMatrixFppnRowEntry 3 }

     ebrNportMatrixFppnRowStatus OBJECT-TYPE
	SYNTAX	INTEGER {
			invalid(1),
			permanent(2)
		}
	ACCESS	read-write
	STATUS	mandatory
	DESCRIPTION "
		Assigning the value invalid will delete the row of the matrix.
		Attempting to delete the last ebrNportmatrixname entry for a
		matrix will result in an error while the matrix is still
		reference by some filter.

		All matrices are permanent; it is their usage which may or may
		not be temporary.
		"
	::= { ebrNportMatrixFppnRowEntry 4 }

    ebrNportDefaultMatrixValue OBJECT-TYPE
	SYNTAX	DisplayString (SIZE (32))
	ACCESS	read-write
	STATUS	mandatory
	DESCRIPTION
		"A matrix is expressed using a shorthand that says what
		input ports can talk to what output ports.

		An examples of a specification is:
			11:1; 1:3-5; 2:0,3; 4-7,9:4-7,9; 10:

		Semicolons separate expressions.  Within each expression,
		the colon has a left hand side and a right hand side.  Bridge
		ports on the left hand side can send packets to bridge ports
		on the right hand side.  Commas separate items in a list of
		bridge ports.  Hyphens are short-hand for specifying a range
		of numbers.  If there is no right hand side, the bridge ports
		on the left cannot send packets to any bridge port (unless the
		matrix is combined with some some other matrix in a filter
		specification, or unless the filter is overridden).

		Bridge port numbers are specified in decimal.

		A matrix will read back in a form equivalent to the form
		written.  It may not read back exactly as written.

		No single matrix defines whether a packet arriving on a port
		is forwarded to its destination.  Various destination address,
		source address, protocol, and default filtering specifications
		are combined to determine whether the packet is forwarded.
		Unspecified rows are set to one's, which means that the
		corresponding input ports can communicate with every 
		output port.
		"
	::= { filterByReferencedExpression 6 }

    ebrNportDefaultMatrixFppnValue OBJECT-TYPE
	SYNTAX	DisplayString (SIZE (32))
	ACCESS	read-write
	STATUS	mandatory
	DESCRIPTION
		"A matrix is expressed using a shorthand that says what
		input front panel ports can talk to what output front
		panel ports.

                An examples of a specification is:
                        1.1,2.1-14.2:1.1-14.2; 2.2:5.3,6.4; 10.3:;

                Semicolons separate expressions.  Within each expression,
                the colon has a left hand side and a right hand side.  Front
                panel ports on the left hand side can send packets to front
                panel ports on the right hand side.  Commas separate items in
                a list of front panel ports.  Hyphens are short-hand for
                specifying a range of numbers.  If there is no right hand side,
                the front panel ports on the left cannot send packets to any
                front panel port (unless the matrix is combined with some some
                other matrix in a filter specification, or unless the filter is
                overridden).

                Front panel port numbers are of the form (slot.connector),
		where slot is the slot number the module is plugged into,
		and connector is the connector number specified on the
		front of the card.

		A matrix will read back in a form equivalent to the form
		written.  It may not read back exactly as written.

		No single matrix defines whether a packet arriving on a port
		is forwarded to its destination.  Various destination address,
		source address, protocol, and default filtering specifications
		are combined to determine whether the packet is forwarded.
		Unspecified rows are set to one's, which means that the
		corresponding input ports can communicate with every 
		output port.
		"
	::= { filterByReferencedExpression 9 }

    ebrNportNamedDefaultMatrix OBJECT-TYPE
	SYNTAX	DisplayString (SIZE (32))
	ACCESS	read-write
	STATUS	mandatory
	DESCRIPTION
		"When a matrix name is written to this object, the default
		matrix is set to the matrix if and only if the matrix
		exists.

		Unspecified rows in the matrix are set to one's, which means 
		that the corresponding input ports can communicate with every 
		output port.
		"
	::= { filterByReferencedExpression 12 }

    ebrNportDefaultMatrixRowTable OBJECT-TYPE
        SYNTAX  SEQUENCE OF EbrNportDefaultMatrixRowEntry
        ACCESS  not-accessible
        STATUS  mandatory
        DESCRIPTION "
                This table is another view of ebrNportDefaultMatrixValue.
                "
        ::= { filterByReferencedExpression 13 }

    ebrNportDefaultMatrixRowEntry OBJECT-TYPE
        SYNTAX  EbrNportDefaultMatrixRowEntry 
        ACCESS  not-accessible
        STATUS  mandatory
        DESCRIPTION "
		A particular row of the default matrix.
		"
        INDEX { ebrNportDefaultMatrixReceivePort }
        ::= { ebrNportDefaultMatrixRowTable 1 }

    EbrNportDefaultMatrixRowEntry ::=
        SEQUENCE {
                ebrNportDefaultMatrixReceivePort   INTEGER,
                ebrNportDefaultMatrixAllowedToGoTo OCTET STRING
        }

    ebrNportDefaultMatrixReceivePort OBJECT-TYPE
	SYNTAX	INTEGER
	ACCESS	read-only
	STATUS	mandatory
	DESCRIPTION
		"A bridge port number."
	::= { ebrNportDefaultMatrixRowEntry 1 }

    ebrNportDefaultMatrixAllowedToGoTo OBJECT-TYPE
	SYNTAX OCTET STRING (SIZE (5))
	ACCESS	read-only
	STATUS	mandatory
	DESCRIPTION
		"The set of ports to which frames received from a specific 
		port are allowed to be forwarded by default.

		Each octet of this object specifies a set of eight ports,
                with the first octet specifying ports 1 through 8,
                the second octet specifying port 9 through 16 etc.
                Within each octet, the most significant bit represents
                the lowest numbered port, and the least significant
                bit represents the highest numbered port.  If a
                bit has a value of '1', then the corresponding port
                is included in the set of ports; the port is not
                included if its bit has a value of '0'.
		"
	::= { ebrNportDefaultMatrixRowEntry 2 }

    ebrNportManualFilter OBJECT-TYPE
	SYNTAX	DisplayString	(SIZE (32))
	ACCESS	read-write
	STATUS	mandatory
	DESCRIPTION
		"The list of bridge ports in manual mode is listed.


                Manual mode means that the bridge purges the learned entries
                for that port from its forwarding database, stops its learning
                process on that port, and forwards to that port only frames
                with destination and source addresses that have been specified
                via management.

		A comma-separated list of bridge ports, with hyphens used to
		abbreviate ranges, is supported.  The bridge port numbers are
		in decimal.
		"
	::= { filterByReferencedExpression 7 }

    ebrNportFppnManualFilter OBJECT-TYPE
	SYNTAX	DisplayString	(SIZE (32))
	ACCESS	read-write
	STATUS	mandatory
	DESCRIPTION
		"The list of front panel ports in manual mode is listed.


                Manual mode means that the bridge purges the learned entries
                for that port from its forwarding database, stops its learning
                process on that port, and forwards to that port only frames
                with destination and source addresses that have been specified
                via management.

		A comma-separated list of front panel ports, with hyphens used 
		to abbreviate ranges, is supported.  

                Front panel port numbers are of the form (slot.connector),
		where slot is the slot number the module is plugged into,
		and connector is the connector number specified on the
		front of the card.
		"
	::= { filterByReferencedExpression 10 }


    --
    -- these are bridge objects over and above what is required by
    -- the Bridge MIB [2]
    --

    filterByBitmapValue OBJECT IDENTIFIER ::= { gigaBridge 2 }

    --  Static Database for N port bridges
 
    -- See ebrNportStaticDAFilterCharacteristicsTable for how to delete
    -- (c.f., overwrite portions of) filter matrices.

    ebrNportStaticDATable OBJECT-TYPE
        SYNTAX  SEQUENCE OF EbrNportStaticDAEntry
        ACCESS  not-accessible
        STATUS  mandatory
        DESCRIPTION
                "This table contains management-specified destination address
		filtering information about unicast and multicast addresses
		for N-port bridges.  In RFC 1286 lingo, static objects are
		those objects which have been specified by network management."
        ::= { filterByBitmapValue 5 }
 
    ebrNportStaticDAEntry OBJECT-TYPE
        SYNTAX  EbrNportStaticDAEntry
        ACCESS  not-accessible
        STATUS  mandatory
        DESCRIPTION
                "Information about a specific MAC address for which the bridge
		has some management-specified forwarding and/or filtering
		information."
        INDEX   { ebrNportDAAddress, ebrNportDAReceivePort }
        ::= { ebrNportStaticDATable 1 }
 
    EbrNportStaticDAEntry ::=
        SEQUENCE {
            ebrNportDAAddress
                OCTET STRING,
            ebrNportDAReceivePort
                INTEGER,
            ebrNportDAAllowedToGoTo
                OCTET STRING
        }
 
    ebrNportDAAddress OBJECT-TYPE
        SYNTAX  OCTET STRING (SIZE (6))
        ACCESS  read-write
        STATUS  mandatory
        DESCRIPTION
                "The destination MAC Address in a frame to
                 which this entry's filtering information applies."
        ::= { ebrNportStaticDAEntry 1 }
 
     ebrNportDAReceivePort OBJECT-TYPE
        SYNTAX  INTEGER
        ACCESS  read-write
        STATUS  mandatory
        DESCRIPTION
                "The port from which a frame must be received to use
                the corresponding ebrNportDAAllowedToGoTo field.

		A value of zero indicates that this entry applies on all ports
		of the bridge for which there is no other applicable entry."
        ::= { ebrNportStaticDAEntry 2 }
 

     ebrNportDAAllowedToGoTo OBJECT-TYPE
        SYNTAX  OCTET STRING (SIZE (5))
        ACCESS  read-write
        STATUS  mandatory
        DESCRIPTION
                "The set of ports to which frames received from
                a specific port and destined to the address specified by
		ebrNportDAAddress are allowed to be forwarded.

		Each octet of this object specifies a set of eight ports,
                with the first octet specifying ports 1 through 8,
                the second octet specifying port 9 through 16 etc.
                Within each octet, the most significant bit represents
                the lowest numbered port, and the least significant
                bit represents the highest numbered port.  If a
                bit has a value of '1', then the corresponding port
                is included in the set of ports; the port is not
                included if its bit has a value of '0'.

		Filter matrix rows can be initialized or overwritten, but not
		deleted.  Only whole matrices are deleted via the
		characteristics table.  To produce the equivalent of row
		deletion, set the GoTo according to the following table:
			Disp				GoTo
			filter/portMask			0xFFFFFFFFF0
			alwaysFilter			0xFFFFFFFFF0
			alwaysForward			0
		"
        ::= { ebrNportStaticDAEntry 3 }



    -- The filtering information is modelled, and implemented, using filter
    -- matrices.  The use (disposition) and permanence (status) of the filtering
    -- information therefore is on a per matrix, not a per row or per element
    -- basis.  The use and permanence are independent of the receiving bridge
    -- port.  Thus we model it in a table distinct from receive port/goto
    -- for emphasis.

    --
    -- Were we to model these with the receive port/goto, writing the
    -- disposition or permanence of one filter matrix row would side-effect
    -- the values in all the other rows.  Also, when dumping
    -- the table, a lot of redundant information would be presented.

    ebrNportStaticDAFilterCharacteristicsTable OBJECT-TYPE
        SYNTAX  SEQUENCE OF EbrNportStaticDAFilterCharacteristicsEntry
        ACCESS  not-accessible
        STATUS  mandatory
        DESCRIPTION
                "A table that contains information about how static destination
		 address filters (for unicast and multicast addresses) are used
		 within N-port bridges. Static objects are those objects which
		 have been specified by network management."
        ::= { filterByBitmapValue 6 }
 
    ebrNportStaticDAFilterCharacteristicsEntry OBJECT-TYPE
        SYNTAX  EbrNportStaticDAFilterCharacteristicsEntry
        ACCESS  not-accessible
        STATUS  mandatory
        DESCRIPTION
                "Information about a specific static MAC destination address
		 filter's usage within N-port bridges."
        INDEX   { ebrNportDestinationAddress }
        ::= { ebrNportStaticDAFilterCharacteristicsTable 1 }
 
    EbrNportStaticDAFilterCharacteristicsEntry ::=
        SEQUENCE {
            ebrNportDestinationAddress
                OCTET STRING,
	    ebrNportDADisp
		INTEGER,
            ebrNportDAStatus
                INTEGER
        }
 
    ebrNportDestinationAddress OBJECT-TYPE
        SYNTAX  OCTET STRING (SIZE (6))
        ACCESS  read-write
        STATUS  mandatory
        DESCRIPTION
                "The destination MAC Address in a frame to which this entry's
		 information applies.  The value of this object is the same
		 as ebrNportDAAddress."
        ::= { ebrNportStaticDAFilterCharacteristicsEntry 1 }
 

    -- Implementations may require a filter matrix to already exist, or to be
    -- simultaneously specified, when writing Disp/Status values.

    ebrNportDADisp OBJECT-TYPE
        SYNTAX  INTEGER {

			filter(1),
			alwaysFilter(2),
			alwaysForward(3)
	}
        ACCESS  read-write
        STATUS  mandatory
        DESCRIPTION
                "This object specifies how to interpret the ebrNportPortNum and
		 ebrNportDAAllowedToGoTo objects.
 

                  filter(1) : The filtering for this address is specified by
			the filter matrix.

		  alwaysFilter(2) : Frames destined to address are filtered
			regardless of any other alwaysForward dispositions
			based on the frame's source address or protocol type.
			The filtering information is specified by the filter
			matrix.

                  alwaysForward(3) : Frames destined to address are always
			forwarded to ebrNportPortNum if specified.
			The filter matrix is used to specify ports to
			which frames may be sent. In both cases, this
			disposition overrides filters based on the frame's
			source address or protocol type, unless either of those
			filters has an alwaysFilter disposition.
		"

        ::= { ebrNportStaticDAFilterCharacteristicsEntry 2 }


    ebrNportDAStatus OBJECT-TYPE
        SYNTAX  INTEGER {

			other(1),
			invalid(2),
			permanent(3),
			deleteOnReset(4),
			deleteOnTimeout(5)
	}
        ACCESS  read-write
        STATUS  mandatory
        DESCRIPTION
		"

		other(1) - This entry is currently in use, but the 
			conditions under which it will remain so are different
			from each of the following values.  Like other uses
			of 'other' in MIBs, this value may not be assigned to
			the object.

		invalid(2) - Writing this value to the object removes the entry

		permanent(3) - Writing this value to the object indicates that
			the entry is preserved across a bridge reset.

		deleteOnReset(4) - Writing this value removes the permanent
			entry characteristic.  The entry is deleted upon the
			next bridge reset (SCP or GIGAswitch failure).

			Writing deleteOnReset is not supported.  SNMP does not
			currently model viewing the non-volatile and volatile
			data structures independently, which can lead to
			unexpectedly having no filter if a reset occurs while
			temporarily trying a change to an existing filter.
			Writes of this value will result in a bad value return
			status.  It is present for consistency with the Bridge
			MIB (RFC 1286), which describes address filters.

		deleteOnTimeout(5) - Writing this value removes the permanent
			entry characteristic.  Since the timers used for aging
			information within the bridge are hidden from the user,
			the change may in fact take place immediately.

			Writing deleteOnTimeout is not supported.  SNMP does not
			currently model viewing the non-volatile and volatile
			data structures independently, which can lead to
			unexpectedly having no filter if a reset occurs while
			temporarily trying a change to an existing filter.
			Writes of this value will result in a bad value return
			status.  It is present for consistency with the Bridge
			MIB (RFC 1286), which describes address filters.
		"
        ::= { ebrNportStaticDAFilterCharacteristicsEntry 3 }

    -- The service class information applies on a box-wide basis, and is
    -- independent of the receiving bridge port.  Thus we model it in a
    -- table distinct from ebrNportStaticDATable for emphasis.
    --
    -- Service class and filtering information can be manipulated independently.

    ebrNportDASvcTable OBJECT-TYPE
        SYNTAX  SEQUENCE OF EbrNportDASvcEntry
        ACCESS  not-accessible
        STATUS  mandatory
        DESCRIPTION
                "A table that contains resource information about unicast and
                 multicast destination addresses for N-port bridges."
        ::= { serviceClassAssignments 3 }
 
    ebrNportDASvcEntry OBJECT-TYPE
        SYNTAX  EbrNportDASvcEntry
        ACCESS  not-accessible
        STATUS  mandatory
        DESCRIPTION
                "Resource information about a specific MAC destination address
                for N-port bridges."
        INDEX   { ebrNportSvcAddress }
        ::= { ebrNportDASvcTable 1 }
 
    EbrNportDASvcEntry ::=
        SEQUENCE {
            ebrNportSvcAddress
                OCTET STRING,
	    ebrNportSvc
		INTEGER,
            ebrNportSvcStatus
                INTEGER
        }
 
    ebrNportSvcAddress OBJECT-TYPE
        SYNTAX  OCTET STRING (SIZE (6))
        ACCESS  read-write
        STATUS  mandatory
        DESCRIPTION
                "The destination MAC Address in a frame to which this entry's
		 resource information applies."
        ::= { ebrNportDASvcEntry 1 }

    ebrNportSvc OBJECT-TYPE
        SYNTAX  INTEGER
        ACCESS  read-write
        STATUS  mandatory
        DESCRIPTION
                "The service class used to allocate resources and implement
		 service policy within the bridge. The service class
		 associated with a frame is a function of either the frame's
		 destination address or the frame's protocol. The default
		 value for this field is 0. This value is used to assign the
		 single path service class in the absence of a service class
		 associated with the frame's protocol.  There are 16 possible
		 service classes, 0-15. The ebrNportSvc allows 32 values to
		 be specified. The specification of a value greater than 15
		 is used to connote  that the service class (ebrNportSvc-16),
		 is to be associated with the frame and that this service
		 class has precedence over a service class associated with
		 a frame's protocol.


	Service classes 1-11 are reserved for internal or future use.
		"
        ::= { ebrNportDASvcEntry 2 }

    ebrNportSvcStatus OBJECT-TYPE
	SYNTAX	INTEGER {

			invalid(1),
			permanent(2)
	}
	ACCESS	read-write
	STATUS	mandatory
	DESCRIPTION
		"

		This object specifies the permanence of the specified service
		class usage, and also provides a means to delete an entry.

                Writing invalid(1) to the object removes the entry.

                Writing permanent(2) value to the object indicates the entry is
                preserved across a bridge reset.
		"
        ::= { ebrNportDASvcEntry 3 }

    -- The port number information applies on a box-wide basis, and is
    -- independent of the receiving bridge port.  Thus we model it in a
    -- table distinct from ebrNportStaticDATable/ebrNportStaticSATable
    -- for emphasis.

    ebrNportPortNumTable OBJECT-TYPE
        SYNTAX  SEQUENCE OF EbrNportPortNumEntry
        ACCESS  not-accessible
        STATUS  mandatory
        DESCRIPTION
                "A table that contains static (i.e., configured by
		 network management) information about the bridge
		 port on which unicast or multicast addresses reside
		 on N-port bridges."
        ::= { gigaBridge 3 }
 
    ebrNportPortNumEntry OBJECT-TYPE
        SYNTAX  EbrNportPortNumEntry
        ACCESS  not-accessible
        STATUS  mandatory
        DESCRIPTION
                "Information about a specific MAC address."
        INDEX   { ebrNportPortNumAddress }
        ::= { ebrNportPortNumTable 1 }
 
    EbrNportPortNumEntry ::=
        SEQUENCE {
            ebrNportPortNumAddress
                OCTET STRING,
            ebrNportPortNum
                INTEGER,
            ebrNportPortNumStatus
                INTEGER,
	    ebrNportFppnPortNum
		DisplayString
        }
 
    ebrNportPortNumAddress OBJECT-TYPE
        SYNTAX  OCTET STRING (SIZE (6))
        ACCESS  read-write
        STATUS  mandatory
        DESCRIPTION
                "The MAC Address to which this entry's information applies."
        ::= { ebrNportPortNumEntry 1 }

    ebrNportPortNum OBJECT-TYPE
        SYNTAX  INTEGER
        ACCESS  read-write
        STATUS  mandatory
        DESCRIPTION
                "The Port Number to which this address will be
                translated (to which frames destined for the address
		will be forwarded).  There are some filtering nuances
		for addresses with specified port numbers which are
		determined by the source address and destination address
		filter disposition characteristics.

		If zero, no port number is specified.

		This value is a giganet destination address instead of a
		bridge port number if it is greater than 127."
        ::= { ebrNportPortNumEntry 2 }

    ebrNportPortNumStatus OBJECT-TYPE
	SYNTAX	INTEGER {

			invalid(1),
			permanent(2)
	}
	ACCESS	read-write
	STATUS	mandatory
	DESCRIPTION
		"

		This object specifies the permanence of the specified
		information, and also provides a means to delete an entry.

                Writing invalid(1) to the object removes the entry.

                Writing permanent(2) value to the object indicates the entry is
                preserved across a bridge reset.
		"
        ::= { ebrNportPortNumEntry 3 }

    ebrNportFppnPortNum OBJECT-TYPE
        SYNTAX  DisplayString
        ACCESS  read-write
        STATUS  mandatory
        DESCRIPTION
                "The Front Panel Port Number to which this address will be
                translated (to which frames destined for the address
		will be forwarded).  There are some filtering nuances
		for addresses with specified front panel port numbers 
		which are determined by the source address and destination 
		address filter disposition characteristics.

		Managers may not specify both ebrNportPortNum and
		ebrNportFppnPortNum at the same time to set an entry 
		in this table."

        ::= { ebrNportPortNumEntry 4 }

    -- See ebrNportStaticSAFilterCharacteristicsTable for how to delete
    -- (c.f., overwrite portions of) filter matrices.

    ebrNportStaticSATable OBJECT-TYPE
        SYNTAX  SEQUENCE OF EbrNportStaticSAEntry
        ACCESS  not-accessible
        STATUS  mandatory
        DESCRIPTION
                "A table that contains static source address filtering
		 information about unicast and multicast addresses for
		 N-port bridges. Static objects are those objects which
		 have been specified by network management."
        ::= { filterByBitmapValue 7 }
 
    ebrNportStaticSAEntry OBJECT-TYPE
        SYNTAX  EbrNportStaticSAEntry
        ACCESS  not-accessible
        STATUS  mandatory
        DESCRIPTION
                "Information about a specific MAC address for which the
		 bridge has some static forwarding and/or filtering
		 information."
        INDEX   { ebrNportSAAddress, ebrNportSAReceivePort }
        ::= { ebrNportStaticSATable 1 }
 
    EbrNportStaticSAEntry ::=
        SEQUENCE {
            ebrNportSAAddress
                OCTET STRING,
            ebrNportSAReceivePort
                INTEGER,
	    ebrNportSAAllowedToGoTo
		OCTET STRING
        }
 
    ebrNportSAAddress OBJECT-TYPE
        SYNTAX  OCTET STRING (SIZE (6))
        ACCESS  read-write
        STATUS  mandatory
        DESCRIPTION
                "The source MAC Address in a frame to which this entry's
		 filtering information applies."
        ::= { ebrNportStaticSAEntry 1 }

     ebrNportSAReceivePort OBJECT-TYPE
        SYNTAX  INTEGER
        ACCESS  read-write
        STATUS  mandatory
        DESCRIPTION
                "The port from which a frame must be received to use
                the corresponding ebrNportSAAllowedToGoTo field.

		A value of zero indicates that this entry applies on all
		ports of the bridge for which there is no other applicable
		entry."
        ::= { ebrNportStaticSAEntry 2 }
 

   ebrNportSAAllowedToGoTo OBJECT-TYPE
        SYNTAX  OCTET STRING (SIZE (5))
        ACCESS  read-write
        STATUS  mandatory
        DESCRIPTION
                "The set of ports to which frames received from
                a specific port and sourced from the address specified by
		ebrNportSAAddress are allowed to be forwarded.

		Each octet of this object specifies a set of eight ports,
                with the first octet specifying ports 1 through 8,
                the second octet specifying port 9 through 16 etc.
                Within each octet, the most significant bit represents
                the lowest numbered port, and the least significant
                bit represents the highest numbered port.  If a
                bit has a value of '1', then the corresponding port
                is included in the set of ports; the port is not
                included if its bit has a value of '0'.

		Filter matrix rows can be initialized or overwritten, but not
		deleted.  Only whole matrices are deleted via the
		characteristics table.  To produce the equivalent of row
		deletion, set the GoTo according to the following table:
			Disp				GoTo
			filter/portMask			0xFFFFFFFFF0
			alwaysFilter			0xFFFFFFFFF0
			alwaysForward			0
		"
        ::= { ebrNportStaticSAEntry 3 }
 


    -- The filtering information is modelled, and implemented, using filter
    -- matrices.  The use (disposition) and permanence (status) of the filtering
    -- information therefore is on a per matrix, not a per row or per element
    -- basis.  The use and permanence are independent of the receiving bridge
    -- port.  Thus we model it in a table distinct from receive port/goto
    -- for emphasis.

    --
    -- Were we to model these with the receive port/goto, writing the
    -- disposition or permanence of one filter matrix row would side-effect
    -- the values in all the other rows.  Also, when dumping
    -- the table, a lot of redundant information would be presented.

    ebrNportStaticSAFilterCharacteristicsTable OBJECT-TYPE
        SYNTAX  SEQUENCE OF EbrNportStaticSAFilterCharacteristicsEntry
        ACCESS  not-accessible
        STATUS  mandatory
        DESCRIPTION
                "A table that contains information about how static source
                 address filters (for unicast and multicast addresses) are
		 used within N-port bridges."
        ::= { filterByBitmapValue 8 }
 
    ebrNportStaticSAFilterCharacteristicsEntry OBJECT-TYPE
        SYNTAX  EbrNportStaticSAFilterCharacteristicsEntry
        ACCESS  not-accessible
        STATUS  mandatory
        DESCRIPTION
                "Static source address filter usage for N-port bridges."
        INDEX   { ebrNportSourceAddress }
        ::= { ebrNportStaticSAFilterCharacteristicsTable 1 }
 
    EbrNportStaticSAFilterCharacteristicsEntry ::=
        SEQUENCE {
            ebrNportSourceAddress
                OCTET STRING,
	    ebrNportSADisp
		INTEGER,
            ebrNportSAStatus
                INTEGER
        }
 
    ebrNportSourceAddress OBJECT-TYPE
        SYNTAX  OCTET STRING (SIZE (6))
        ACCESS  read-write
        STATUS  mandatory
        DESCRIPTION
                "The source MAC Address in a frame to which this entry's
		 information applies.  The value of this object is the
		 same as ebrNportSAAddress."
        ::= { ebrNportStaticSAFilterCharacteristicsEntry 1 }


    -- Implementations may require a filter matrix to already exist, or to be
    -- simultaneously specified, when writing Disp/Status values.

    ebrNportSADisp OBJECT-TYPE
        SYNTAX  INTEGER {

                  portMask(1),
		  alwaysFilter(2),
                  alwaysForward(3),
		  lockdown(4),
		  lockdownportmask(5),
		  filter(6)
	}
        ACCESS  read-write
        STATUS  mandatory
        DESCRIPTION
                "This object specifies how to interpret the ebrNportPortNum and
		 and the ebrNportSAAllowedToGoTo objects.
 

                  portMask(1) : The static filtering for this address
                      is specified by the filter matrix.

		  alwaysFilter(2) : Frames sourced from this address are
			filtered regardless of any other alwaysForward
			dispositions based on the frame's destination address
			or protocol type. The static filtering information is
			specified by the filter matrix.

                  alwaysForward(3) : Frames sourced from this address are
			sent to ports specified in the filter matrix
			regardless of any DA or protocol filter with a
			disposition of filter. The alwaysForward disposition
			also overrides a forwarding disposition of filter
			in the default filter matrix object.

			Filters with a disposition of alwaysFilter are never
			superceded.

		  lockdown (4) : Frames sourced from this address
			are ONLY forwarded if received on the same port as
			ebrNportPortNum.

		  lockdownportmask (5) : Frames sourced from this address
			are ONLY forwarded if received on the same port as
			ebrNportPortNum AND if the frame is destined to a
			permitted port as specified by the filter matrix.

                  filter(6) : The static filtering for this address
                      is specified by the filter matrix.  portMask(1) is
		      the different name with the same effect.
		"

        ::= { ebrNportStaticSAFilterCharacteristicsEntry 2 }


    ebrNportSAStatus OBJECT-TYPE
        SYNTAX  INTEGER {

			other(1),
			invalid(2),
			permanent(3),
			deleteOnReset(4),
			deleteOnTimeout(5)
	}
        ACCESS  read-write
        STATUS  mandatory
        DESCRIPTION
		"

		other(1) - This entry is currently in use, but the 
			conditions under which it will remain so are different
			from each of the following values.  Like other uses
			of 'other' in MIBs, this value may not be assigned to
			the object.

		invalid(2) - Writing this value to the object removes the entry

		permanent(3) - Writing this value to the object indicates that
			the entry is preserved across a bridge reset.

		deleteOnReset(4) - Writing this value removes the permanent
			entry characteristic.  The entry is deleted upon the
			next bridge reset (SCP or GIGAswitch failure).

			Writing deleteOnReset is not supported.  SNMP does not
			currently model viewing the non-volatile and volatile
			data structures independently, which can lead to
			unexpectedly having no filter if a reset occurs while
			temporarily trying a change to an existing filter.
			Writes of this value will result in a bad value return
			status.  It is present for consistency with the Bridge
			MIB (RFC 1286), which describes address filters.

		deleteOnTimeout(5) - Writing this value removes the permanent
			entry characteristic.  Since the timers used for aging
			information within the bridge are hidden from the user,
			the change may in fact take place immediately.

			Writing deleteOnTimeout is not supported.  SNMP does not
			currently model viewing the non-volatile and volatile
			data structures independently, which can lead to
			unexpectedly having no filter if a reset occurs while
			temporarily trying a change to an existing filter.
			Writes of this value will result in a bad value return
			status.  It is present for consistency with the Bridge
			MIB (RFC 1286), which describes address filters.
		"

        ::= { ebrNportStaticSAFilterCharacteristicsEntry 3 }



    --  Protocol Database for N-port bridges
 
    -- See ebrNportSapFilterCharacteristicsTable for how to delete (c.f.,
    -- overwrite portions of) filter matrices.

    ebrNportSapProtoTable OBJECT-TYPE
        SYNTAX  SEQUENCE OF EbrNportSapProtoEntry
        ACCESS  not-accessible
        STATUS  mandatory
        DESCRIPTION
                "A table that contains filtering information about
                802.2 SAPs in the DSAP field for N-port bridges."
        ::= { filterByBitmapValue 1 }
 
    ebrNportSapProtoEntry OBJECT-TYPE
        SYNTAX  EbrNportSapProtoEntry
        ACCESS  not-accessible
        STATUS  mandatory
        DESCRIPTION
                "A table that contains filtering information about
                802.2 SAPs in the DSAP field for N-port bridges."
        INDEX   { ebrNportSapValue, ebrNportSapReceivePort }
        ::= { ebrNportSapProtoTable 1 }

    EbrNportSapProtoEntry ::=
        SEQUENCE {
            ebrNportSapValue
                OCTET STRING,
            ebrNportSapReceivePort
                INTEGER,
            ebrNportSapAllowedToGoTo
                OCTET STRING
                 }
    ebrNportSapValue OBJECT-TYPE
        SYNTAX  OCTET STRING (SIZE (1))
        ACCESS  read-write
        STATUS  mandatory
        DESCRIPTION
                "The 802.2 DSAP in a frame to which this entry's
                filtering information applies."
        ::= { ebrNportSapProtoEntry 1 }
 
    ebrNportSapReceivePort OBJECT-TYPE
        SYNTAX  INTEGER
        ACCESS  read-write
        STATUS  mandatory
        DESCRIPTION

                "The port from which a frame must be received to use
                the corresponding ebrNportSapAllowedToGoTo. A value of
		zero indicates that this entry applies on all ports of
		the bridge for which there is no other applicable entry."

        ::= { ebrNportSapProtoEntry 2 }
 

    ebrNportSapAllowedToGoTo OBJECT-TYPE
        SYNTAX  OCTET STRING (SIZE (5))
        ACCESS  read-write
        STATUS  mandatory
        DESCRIPTION
                "The set of ports to which frames received from
                a specific port and containing the DSAP in an 802
                frame specified by ebrNportSapValue are
                allowed to be forwarded.

		Each octet of this object specifies a set of eight ports,
                with the first octet specifying ports 1 through 8,
                the second octet specifying port 9 through 16 etc.
                Within each octet, the most significant bit represents
                the lowest numbered port, and the least significant
                bit represents the highest numbered port.  If a
                bit has a value of '1', then the corresponding port
                is included in the set of ports; the port is not
                included if its bit has a value of '0'.

		Filter matrix rows can be initialized or overwritten, but not
		deleted.  Only whole matrices are deleted via the
		characteristics table.  To produce the equivalent of row
		deletion, set the GoTo according to the following table:
			Disp				GoTo
			filter/portMask			0xFFFFFFFFF0
			alwaysFilter			0xFFFFFFFFF0
			alwaysForward			0
		"
        ::= { ebrNportSapProtoEntry 3 }


    -- The service class information applies on a box-wide basis, and is
    -- independent of the receiving bridge port.  Thus we model it in a
    -- table distinct from ebrNportSapProtoTable for emphasis.
    --
    -- Since the ebrNportSapSvcTable and ebrNportSapProtoTable have independent
    -- status values, the service class and filtering information can be
    -- manipulated independently.

    ebrNportSapSvcTable OBJECT-TYPE
        SYNTAX  SEQUENCE OF EbrNportSapSvcEntry
        ACCESS  not-accessible
        STATUS  mandatory
        DESCRIPTION
                "A table that contains resource information (e.g., queuing)
		about 802.2 SAPs in the DSAP field for N-port bridges."
        ::= { serviceClassAssignments 1 }
 
    ebrNportSapSvcEntry OBJECT-TYPE
        SYNTAX  EbrNportSapSvcEntry
        ACCESS  not-accessible
        STATUS  mandatory
        DESCRIPTION
                "Resource information about an 802.2 SAP in the DSAP field
		for N-port bridges."
        INDEX   { ebrNportSapSvcSapValue }
        ::= { ebrNportSapSvcTable 1 }

    EbrNportSapSvcEntry ::=
        SEQUENCE {
            ebrNportSapSvcSapValue
                OCTET STRING,
	    ebrNportSapSvc
		INTEGER,
	    ebrNportSapSvcStatus
		INTEGER 
	}

    ebrNportSapSvcSapValue OBJECT-TYPE
        SYNTAX  OCTET STRING (SIZE (1))
        ACCESS  read-write
        STATUS  mandatory
        DESCRIPTION
                "The 802.2 DSAP in a frame to which this entry's
                resource information applies."
        ::= { ebrNportSapSvcEntry 1 }

    ebrNportSapSvc OBJECT-TYPE
	SYNTAX	INTEGER
        ACCESS  read-write
        STATUS  mandatory
        DESCRIPTION
                "The service class used to allocate resources and implement
		 service policy within the bridge. The service class
		 associated with a frame is a function of either the frame's
		 destination address or the frame's protocol. The default
		 value for this field is 0. This value is used to assign the
		 single path service class  in the absence of an overriding
		 service class associated with the frame's destination addr.
		 There are 16 possible service classes, 0-15.


	Service classes 1-11 are reserved for internal or future use.
		"
        ::= { ebrNportSapSvcEntry 2 }

    ebrNportSapSvcStatus OBJECT-TYPE
        SYNTAX  INTEGER {

			invalid(1),
			permanent(2)
		}
        ACCESS  read-write
        STATUS  mandatory
        DESCRIPTION
		"

		This object specifies the permanence of the specified service
		class usage, and also provides a means to delete an entry.

                Writing invalid(1) to the object removes the entry.

                Writing permanent(2) value to the object indicates the entry is
                preserved across a bridge reset.
		"
        ::= { ebrNportSapSvcEntry 3 }



    -- The filtering information is modelled, and implemented, using filter
    -- matrices.  The use (disposition) and permanence (status) of the filtering
    -- information therefore is on a per matrix, not a per row or per element
    -- basis.  The use and permanence are independent of the receiving bridge
    -- port.  Thus we model it in a table distinct from receive port/goto
    -- for emphasis.

    --
    -- Were we to model these with the receive port/goto, writing the
    -- disposition or permanence of one filter matrix row would side-effect
    -- the values in all the other rows.  Also, when dumping
    -- the table, a lot of redundant information would be presented.

    ebrNportSapFilterCharacteristicsTable OBJECT-TYPE
        SYNTAX  SEQUENCE OF EbrNportSapFilterCharacteristicsEntry
        ACCESS  not-accessible
        STATUS  mandatory
        DESCRIPTION
                "A table that contains information about how 802.2 DSAP
		filters are used within N-port bridges."
        ::= { filterByBitmapValue 2 }
 
    ebrNportSapFilterCharacteristicsEntry OBJECT-TYPE
        SYNTAX  EbrNportSapFilterCharacteristicsEntry
        ACCESS  not-accessible
        STATUS  mandatory
        DESCRIPTION
                "802.2 DSAP filter usage for N-port bridges."
        INDEX   { ebrNportSapFilterCharacteristicsSapValue }
        ::= { ebrNportSapFilterCharacteristicsTable 1 }

    EbrNportSapFilterCharacteristicsEntry ::=
        SEQUENCE {
            ebrNportSapFilterCharacteristicsSapValue
                OCTET STRING,
	    ebrNportSapDisp
		INTEGER,
            ebrNportSapStatus
                INTEGER
	}

    ebrNportSapFilterCharacteristicsSapValue OBJECT-TYPE
        SYNTAX  OCTET STRING (SIZE (1))
        ACCESS  read-write
        STATUS  mandatory
        DESCRIPTION
                "The 802.2 DSAP in a frame to which this entry's
                information applies.  The value of this object is
		the same as ebrNportSapValue."
        ::= { ebrNportSapFilterCharacteristicsEntry 1 }

    ebrNportSapDisp OBJECT-TYPE
        SYNTAX  INTEGER {

                           filter(1),
			   alwaysFilter(2),
                           alwaysForward(3)
                        }

        ACCESS  read-write
        STATUS  mandatory
        DESCRIPTION
                "This object specifies how to interpret the
		ebrNportSapAllowedToGoTo values for the specified SAP.


                  filter(1) : The filtering for this SAP is specified by the
			filter matrix.

		  alwaysFilter(2) : Frames of this SAP (protocol) are
			filtered regardless of any other alwaysForward
			dispositions based on the frame's address.
			The filtering information is specified by the
			filter matrix.

                  alwaysForward(3) : Frames for this SAP (protocol) are
			sent to ports specified in the filter matrix
			regardless of any address filter with a
			disposition of filter. The alwaysForward disposition
			also overrides a forwarding disposition of filter
			in the default filter matrix object.

			Filters with a disposition of alwaysFilter are never
			superceded.
		"
        ::= { ebrNportSapFilterCharacteristicsEntry 2 }

    ebrNportSapStatus OBJECT-TYPE
        SYNTAX  INTEGER  {

			invalid(1),
			permanent(2)
	}
        ACCESS  read-write
        STATUS  mandatory
        DESCRIPTION
		"

		This object specifies the permanence of the associated filter
		matrix, and also provides a means to delete a filter matrix.

                Writing invalid(1) to the object removes the filter.

                Writing permanent(2) value to the object indicates the filter is
                preserved across a bridge reset.
		"
        ::= { ebrNportSapFilterCharacteristicsEntry 3 }



    -- See ebrNportSnapFilterCharacteristicsTable for how to delete
    -- (c.f., overwrite portions of) filter matrices

    ebrNportSnapProtoTable OBJECT-TYPE
        SYNTAX  SEQUENCE OF EbrNportSnapProtoEntry
        ACCESS  not-accessible
        STATUS  mandatory
        DESCRIPTION
                "A table that contains filtering information about
                5-byte SNAP Protocol IDs (PIDs) for N-port bridges."
        ::= { filterByBitmapValue 3 }

    ebrNportSnapProtoEntry OBJECT-TYPE
        SYNTAX  EbrNportSnapProtoEntry
        ACCESS  not-accessible
        STATUS  mandatory
        DESCRIPTION
                "A table that contains filtering information about
                5-byte SNAP Protocol IDs (PIDs) for N-port bridges."
        INDEX   { ebrNportSnapValue, ebrNportSnapReceivePort }
        ::= { ebrNportSnapProtoTable 1 }

    EbrNportSnapProtoEntry ::=
        SEQUENCE {
            ebrNportSnapValue
                OCTET STRING,
            ebrNportSnapReceivePort
                INTEGER,
            ebrNportSnapAllowedToGoTo
                OCTET STRING
                 }

      ebrNportSnapValue OBJECT-TYPE
        SYNTAX  OCTET STRING (SIZE (5))
        ACCESS  read-write
        STATUS  mandatory
        DESCRIPTION
                "The SNAP Protocol ID (PID) in an 802 frame to which this
		entry's filtering information applies."
        ::= { ebrNportSnapProtoEntry 1 }
 
    ebrNportSnapReceivePort OBJECT-TYPE
        SYNTAX  INTEGER
        ACCESS  read-write
        STATUS  mandatory
        DESCRIPTION

                "The port from which a frame must be received to use
                the corresponding ebrNportSnapAllowedToGoTo. A value of
		zero indicates that this entry applies on all ports of
		the bridge for which there is no other applicable entry."
        ::= { ebrNportSnapProtoEntry 2 }


    ebrNportSnapAllowedToGoTo OBJECT-TYPE
        SYNTAX  OCTET STRING (SIZE (5))
        ACCESS  read-write
        STATUS  mandatory
        DESCRIPTION
                "The set of ports to which frames received from
                a specific port and containing the SNAP PID in an
                802 frame specified by ebrNportSnapValue are
                allowed to be forwarded.

		Each octet of this object specifies a set of eight ports,
                with the first octet specifying ports 1 through 8,
                the second octet specifying port 9 through 16 etc.
                Within each octet, the most significant bit represents
                the lowest numbered port, and the least significant
                bit represents the highest numbered port.  If a
                bit has a value of '1', then the corresponding port
                is included in the set of ports; the port is not
                included if its bit has a value of '0'.

		Filter matrix rows can be initialized or overwritten, but not
		deleted.  Only whole matrices are deleted via the
		characteristics table.  To produce the equivalent of row
		deletion, set the GoTo according to the following table:
			Disp				GoTo
			filter/portMask			0xFFFFFFFFF0
			alwaysFilter			0xFFFFFFFFF0
			alwaysForward			0
		"
        ::= { ebrNportSnapProtoEntry 3 }


    -- The service class information applies on a box-wide basis, and is
    -- independent of the receiving bridge port.  Thus we model it in a
    -- table distinct from ebrNportSnapProtoTable for emphasis.
    --
    -- Since the ebrNportSnapSvcTable and ebrNportSnapProtoTable have
    -- independent status values, the service class and filtering information
    -- can be manipulated independently.

    ebrNportSnapSvcTable OBJECT-TYPE
        SYNTAX  SEQUENCE OF EbrNportSnapSvcEntry
        ACCESS  not-accessible
        STATUS  mandatory
        DESCRIPTION
                "A table that contains resource information (e.g., queuing)
		about 5-byte SNAP Protocol IDs (PIDs) for N-port bridges."
        ::= { serviceClassAssignments 2 }
 
    ebrNportSnapSvcEntry OBJECT-TYPE
        SYNTAX  EbrNportSnapSvcEntry
        ACCESS  not-accessible
        STATUS  mandatory
        DESCRIPTION
                "Resource information about a 5-byte SNAP Protocol ID (PID)
		for N-port bridges."
        INDEX   { ebrNportSnapSvcSnapValue }
        ::= { ebrNportSnapSvcTable 1 }

    EbrNportSnapSvcEntry ::=
        SEQUENCE {
            ebrNportSnapSvcSnapValue
                OCTET STRING,
	    ebrNportSnapSvc
		INTEGER,
	    ebrNportSnapSvcStatus
		INTEGER 
	}

    ebrNportSnapSvcSnapValue OBJECT-TYPE
        SYNTAX  OCTET STRING (SIZE (1))
        ACCESS  read-write
        STATUS  mandatory
        DESCRIPTION
                "The SNAP Protocol ID (PID) in a frame to which this entry's
                resource information applies."
        ::= { ebrNportSnapSvcEntry 1 }

    ebrNportSnapSvc OBJECT-TYPE
	SYNTAX	INTEGER
        ACCESS  read-write
        STATUS  mandatory
        DESCRIPTION
                "The service class used to allocate resources and implement
		 service policy within the bridge. The service class
		 associated with a frame is a function of either the frame's
		 destination address or the frame's protocol. The default
		 value for this field is 0. This value is used to assign the
		 single path service class  in the absence of an overriding
		 service class associated with the frame's destination addr.
		 There are 16 possible service classes, 0-15.


	Service classes 1-11 are reserved for internal or future use.
		"

        ::= { ebrNportSnapSvcEntry 2 }

    ebrNportSnapSvcStatus OBJECT-TYPE
        SYNTAX  INTEGER {

			invalid(1),
			permanent(2)
		}
        ACCESS  read-write
        STATUS  mandatory
        DESCRIPTION
		"

		This object specifies the permanence of the specified service
		class usage, and also provides a means to delete an entry.

                Writing invalid(1) to the object removes the entry.

                Writing permanent(2) value to the object indicates the entry is
                preserved across a bridge reset.
		"
        ::= { ebrNportSnapSvcEntry 3 }



    -- The filtering information is modelled, and implemented, using filter
    -- matrices.  The use (disposition) and permanence (status) of the filtering
    -- information therefore is on a per matrix, not a per row or per element
    -- basis.  The use and permanence are independent of the receiving bridge
    -- port.  Thus we model it in a table distinct from receive port/goto
    -- for emphasis.

    --
    -- Were we to model these with the receive port/goto, writing the
    -- disposition or permanence of one filter matrix row would side-effect
    -- the values in all the other rows.  Also, when dumping
    -- the table, a lot of redundant information would be presented.

    ebrNportSnapFilterCharacteristicsTable OBJECT-TYPE
        SYNTAX  SEQUENCE OF EbrNportSnapFilterCharacteristicsEntry
        ACCESS  not-accessible
        STATUS  mandatory
        DESCRIPTION
                "A table that contains information about how SNAP Protocol ID
		(PID) filters are used within N-port bridges."
        ::= { filterByBitmapValue 4 }
 
    ebrNportSnapFilterCharacteristicsEntry OBJECT-TYPE
        SYNTAX  EbrNportSnapFilterCharacteristicsEntry
        ACCESS  not-accessible
        STATUS  mandatory
        DESCRIPTION
                "802.2 SNAP Protocol ID (PID) filter usage for N-port bridges."
        INDEX   { ebrNportSnapFilterCharacteristicsSnapValue }
        ::= { ebrNportSnapFilterCharacteristicsTable 1 }

    EbrNportSnapFilterCharacteristicsEntry ::=
        SEQUENCE {
            ebrNportSnapFilterCharacteristicsSnapValue
                OCTET STRING,
	    ebrNportSnapDisp
		INTEGER,
            ebrNportSnapStatus
                INTEGER
	}

    ebrNportSnapFilterCharacteristicsSnapValue OBJECT-TYPE
        SYNTAX  OCTET STRING (SIZE (1))
        ACCESS  read-write
        STATUS  mandatory
        DESCRIPTION
                "The SNAP Protocol ID (PID) in a frame to which this entry's
                information applies.  The value of this object is the same as
		ebrNportSnapValue."
        ::= { ebrNportSnapFilterCharacteristicsEntry 1 }

    ebrNportSnapDisp OBJECT-TYPE
        SYNTAX  INTEGER {

                           filter(1),
			   alwaysFilter(2),
                           alwaysForward(3)
                        }

        ACCESS  read-write
        STATUS  mandatory
        DESCRIPTION
                "This object specifies how to interpret the
		ebrNportSnapAllowedToGoTo values for the specified SNAP PID.
 

                  filter(1) : The filtering for this Protocol ID
                      is specified by the filter matrix.

		  alwaysFilter(2) : Frames of this Protocol ID are
			filtered regardless of any other alwaysForward
			dispositions based on the frame's address.
			The filtering information is specified by the
			filter matrix.

                  alwaysForward(3) : Frames for this Protocol ID are
			sent to ports specified in the filter matrix
			regardless of any address filter with a
			disposition of filter. The alwaysForward disposition
			also overrides a forwarding disposition of filter
			in the default filter matrix object.

			Filters with a disposition of alwaysFilter are never
			superceded.
		"
        ::= { ebrNportSnapFilterCharacteristicsEntry 2 }


    ebrNportSnapStatus OBJECT-TYPE
        SYNTAX  INTEGER {

			invalid(1),
			permanent(2)
	}
        ACCESS  read-write
        STATUS  mandatory
        DESCRIPTION
		"

		This object specifies the permanence of the associated filter
		matrix, and also provides a means to delete a filter matrix.

                Writing invalid(1) to the object removes the filter.

                Writing permanent(2) value to the object indicates the filter is
                preserved across a bridge reset.
		"
        ::= { ebrNportSnapFilterCharacteristicsEntry 3 }


    ebrNportSwTable OBJECT-TYPE
        SYNTAX  SEQUENCE OF EbrNportSwEntry
        ACCESS  not-accessible
        STATUS  mandatory
        DESCRIPTION
               "This table describes the default filter matrix."
        ::= { filterByBitmapValue 9 }

    ebrNportSwEntry OBJECT-TYPE
        SYNTAX  EbrNportSwEntry
        ACCESS  not-accessible
        STATUS  mandatory
        DESCRIPTION
               "The entry describes a row of the default filter matrix."
        INDEX  { ebrNportSwReceivePort }
        ::= { ebrNportSwTable 1 }

    EbrNportSwEntry ::=
        SEQUENCE {
            ebrNportSwReceivePort
                INTEGER,
	    ebrNportSwAllowedToGoTo
		OCTET STRING
            }

    ebrNportSwReceivePort OBJECT-TYPE
        SYNTAX  INTEGER
        ACCESS  read-write
        STATUS  mandatory
        DESCRIPTION
               "The bridge port on which a frame must be received to use
		the corresponding ebrNportSwAllowedToGoTo field.

		A value of zero indicates that this entry applies on all ports
		of the bridge for which there is no other management-specified
		entry."
        ::= { ebrNportSwEntry 1 }


    ebrNportSwAllowedToGoTo OBJECT-TYPE
        SYNTAX  OCTET STRING (SIZE (5))
        ACCESS  read-write
        STATUS  mandatory
        DESCRIPTION
                "This object specifies the default forwarding disposition
		after all DA, SA, and protocol filters have been applied.
		For those cases where no filter applies to the frame, the
		forwarding disposition for the frames received on the
		ebrNportSwReceivePort interface and sent to one or all of the
		bridge's interfaces is determined by the
		ebrNportSwAllowedToGoTo object.

		Each octet of this object specifies a set of eight ports,
                with the first octet specifying ports 1 through 8,
                the second octet specifying port 9 through 16 etc.
                Within each octet, the most significant bit represents
                the lowest numbered port, and the least significant
                bit represents the highest numbered port.  If a
                bit has a value of '1', then the corresponding port
                is included in the set of ports; the port is not
                included if its bit has a value of '0'.
		"

        ::= { ebrNportSwEntry 2 }

    ebrNportSwManualFilter OBJECT-TYPE
        SYNTAX  OCTET STRING (SIZE (5))
        ACCESS  read-write
        STATUS  mandatory
        DESCRIPTION
               "A switch that controls address filtering.  Specifying a
		one in a bit position says that the port is in manual
		mode.

		Each octet of this object specifies a set of eight ports,
                with the first octet specifying ports 1 through 8,
                the second octet specifying port 9 through 16 etc.
                Within each octet, the most significant bit represents
                the lowest numbered port, and the least significant
                bit represents the highest numbered port.  If a
                bit has a value of '1', then the corresponding port
                is included in the set of ports; the port is not
                included if its bit has a value of '0'.

		Manual mode means that the bridge purges the learned entries
		for that port from its forwarding database, stops its learning
		process on that port, and forwards to that port only frames
		with destination and source addresses that have been specified
		via management."
        ::= { filterByBitmapValue 10 }

    cutThrough OBJECT IDENTIFIER ::= { gigaBridge 7 }

    cutThroughTable OBJECT-TYPE
	SYNTAX	SEQUENCE OF CutThroughEntry
	ACCESS	not-accessible
	STATUS	mandatory
	DESCRIPTION
		"This table controls the enabling of some hardware performance
		enhancements that avoid store-and-forward delays during packet
		forwarding, whenever possible."
	::= { cutThrough 1 }

    cutThroughEntry OBJECT-TYPE
	SYNTAX	CutThroughEntry
	ACCESS	not-accessible
	STATUS	mandatory
	DESCRIPTION
		"Information about the enabling of some hardware performance
		enhancements that avoid store-and-forward delays for a specific
		bridge port."
	INDEX	{ cutThroughBridgePort }
	::= { cutThroughTable 1 }

    CutThroughEntry ::=
	SEQUENCE {
		cutThroughBridgePort
			INTEGER,
		cutThroughInbound
			INTEGER,
		cutThroughOutbound
			INTEGER
	}

    cutThroughBridgePort OBJECT-TYPE
	SYNTAX	INTEGER
	ACCESS	read-write
	STATUS	mandatory
	DESCRIPTION
		"The dot1dBasePort bridge port number for this table entry."
	::= { cutThroughEntry 1 }

    cutThroughInbound OBJECT-TYPE
	SYNTAX INTEGER {
		true(1),
		false(2)
	}
	ACCESS	read-write
	STATUS	mandatory
	DESCRIPTION
		"If true, some hardware performance enhancements are enabled
		to avoid store-and-forward delays when packets enter the
		GIGAswitch.

		If false, the whole packet is buffered on the line card at
		which the packet enters the GIGAswitch before it is sent
		to the line card at which the packet leaves the GIGAswitch.

		Cut-through is normally enabled."
	::= { cutThroughEntry 2 }

    cutThroughOutbound OBJECT-TYPE
	SYNTAX INTEGER {
		true(1),
		false(2)
	}
	ACCESS	read-write
	STATUS	mandatory
	DESCRIPTION
		"If true, some hardware performance enhancements are enabled
		to avoid store-and-forward delays when packets leave the
		GIGAswitch.

		If false, the whole packet is buffered on the line card at
		which the packet leaves the GIGAswitch before it is sent
		out of the GIGAswitch.

		Cut-through is normally enabled."
	::= { cutThroughEntry 3 }

    cutThroughFppnTable OBJECT-TYPE
	SYNTAX	SEQUENCE OF CutThroughFppnEntry
	ACCESS	not-accessible
	STATUS	mandatory
	DESCRIPTION
		"This table controls the enabling of some hardware performance
		enhancements that avoid store-and-forward delays during packet
		forwarding, whenever possible."
	::= { cutThrough 2 }

    cutThroughFppnEntry OBJECT-TYPE
	SYNTAX	CutThroughFppnEntry
	ACCESS	not-accessible
	STATUS	mandatory
	DESCRIPTION
		"Information about the enabling of some hardware performance
		enhancements that avoid store-and-forward delays for a specific
		front panel port."
	INDEX	{ cutThroughFppnPort }
	::= { cutThroughFppnTable 1 }

    CutThroughFppnEntry ::=
	SEQUENCE {
		cutThroughFppnPort
			DisplayString,
		cutThroughFppnInbound
			INTEGER,
		cutThroughFppnOutbound
			INTEGER
	}

    cutThroughFppnPort OBJECT-TYPE
	SYNTAX	DisplayString
	ACCESS	read-write
	STATUS	mandatory
	DESCRIPTION
		"The front panel port number for this table entry.

                Front panel port numbers are of the form (slot.connector),
		where slot is the slot number the module is plugged into,
		and connector is the connector number specified on the
		front of the card.

		"
	::= { cutThroughFppnEntry 1 }

    cutThroughFppnInbound OBJECT-TYPE
	SYNTAX INTEGER {
		true(1),
		false(2)
	}
	ACCESS	read-write
	STATUS	mandatory
	DESCRIPTION
		"If true, some hardware performance enhancements are enabled
		to avoid store-and-forward delays when packets enter the
		GIGAswitch.

		If false, the whole packet is buffered on the line card at
		which the packet enters the GIGAswitch before it is sent
		to the line card at which the packet leaves the GIGAswitch.

		Cut-through is normally enabled."
	::= { cutThroughFppnEntry 2 }

    cutThroughFppnOutbound OBJECT-TYPE
	SYNTAX INTEGER {
		true(1),
		false(2)
	}
	ACCESS	read-write
	STATUS	mandatory
	DESCRIPTION
		"If true, some hardware performance enhancements are enabled
		to avoid store-and-forward delays when packets leave the
		GIGAswitch.

		If false, the whole packet is buffered on the line card at
		which the packet leaves the GIGAswitch before it is sent
		out of the GIGAswitch.

		Cut-through is normally enabled."
	::= { cutThroughFppnEntry 3 }

-- the gigaBox group 

-- subgroups under the gigaBox group

	clockCard	OBJECT IDENTIFIER ::= { gigaBox 1 }

	psc         	OBJECT IDENTIFIER ::= { gigaBox 2 }

	powerSupply	OBJECT IDENTIFIER ::= { gigaBox 3 }

	slot		OBJECT IDENTIFIER ::= { gigaBox 4 }

	fan		OBJECT IDENTIFIER ::= { gigaBox 5 }

	battery		OBJECT IDENTIFIER ::= { gigaBox 6 }

	fppn		OBJECT IDENTIFIER ::= { gigaBox 7 }

	lineCard	OBJECT IDENTIFIER ::= { gigaBox 8 }

-- The clockCard subgroup
-- clock card Firmware and hardware rev can be obtained from
-- slotTable. would be redundant if placed here too.

	mgmtMemoryAvail OBJECT-TYPE
		SYNTAX	INTEGER
		ACCESS	read-only
		STATUS	mandatory
		DESCRIPTION
			"The number of unused bytes of management 
			 memory available on the clock card. The 
	                 management memory is used for storing 
			 management parameters."
	::= { clockCard 1 }

	mgmtMemoryAction OBJECT-TYPE
		SYNTAX	INTEGER {
			   other(1),
			   rewrite(2),
			   rewriting(3)
			}
		ACCESS	read-write
		STATUS	mandatory
		DESCRIPTION
			"This object, when read, returns a value of other(1)
			unless it is in the middle of rewriting the management
			memory. At such times, it will return rewriting(3).
			The state will revert to other(1) when the action is
			completed.

			Setting this variable to rewrite(2) will cause the SCP
			to attempt to rewrite the management Memory on the 
			clock-card.  Attempts to set this variable to all other
	                values result in an error.

			Rewriting the management memory gets rid of
	                duplicate entries, and thus may increase the
	                available space.  This action should be allowed
			to complete before intentionally removing power
			from the SCP or clock card.
			"
	::= { clockCard 2  }

-- The psc subgroup (Power System Controller)

	pscStatus OBJECT-TYPE
		SYNTAX	INTEGER {
			   notPresent(1),
			   okay(2),
			   fault(3)
			}
		ACCESS	read-only
		STATUS	mandatory
		DESCRIPTION
			"The status of the Power System Controller (PSC)."
	::= { psc 1 }


	pscFwRev OBJECT-TYPE
		SYNTAX	DisplayString
		ACCESS	read-only
		STATUS	mandatory
		DESCRIPTION
			"The firmware revision of the Power System Controller
			(PSC)."
	::= { psc 2 }


	pscHwRev OBJECT-TYPE
		SYNTAX	DisplayString
		ACCESS	read-only
		STATUS	mandatory
		DESCRIPTION
			"The hardware revision of the Power System Controller
			(PSC)."
	::= { psc 3 }


	keyswitchPosition OBJECT-TYPE
		SYNTAX	INTEGER {
			    fault(1),
			    secure(2),
			    local(3),
	                    remote(4),
                            worldAccess(5)
		        }
		ACCESS	read-only
		STATUS	mandatory
		DESCRIPTION
			"Indicates the position of the keyswitch. The
	                keyswitch position determines the type of
	                access allowed to network management and to
			out-of-band management.

			For SNMP access, secure means no SNMP access.
			Local means read-only SNMP access.  Other values
			allow read-write SNMP access.  All access is
			still  subject to the community string, IP address,
			and privileged port restrictions.
			"
	::= { psc 4 }

	pscFwImageStatus OBJECT-TYPE
		SYNTAX	INTEGER {
			   okay(1),
			   downloadRequired(2)
			}
		ACCESS	read-only
		STATUS	mandatory
		DESCRIPTION
			"The status of the PSC firmware image. If
	                 the value of this object is
	                 downloadRequired(2), the manager should
	                 download a new firmware image to the PSC.
	                 This can be done by using objects in the
	                 gigaUpgradeSoftware group."
	::= { psc 5 }

	pscBackplaneStatus OBJECT-TYPE
		SYNTAX	INTEGER {
			   okay(1),
			   fault(2)
			}
		ACCESS	read-only
		STATUS	mandatory
		DESCRIPTION
			"Status of the GIGAswitch backplane."
	::= { psc 6 }

	cabinetTemperature OBJECT-TYPE
		SYNTAX	INTEGER {
			    normal(1),
			    high(2),
			    excessivelyHigh(3),
	                    low(4),
                            excessivelyLow(5)
		        }
		ACCESS	read-only
		STATUS	mandatory
		DESCRIPTION
			"The cabinet temperature."
	::= { psc 7 }

	temperatureWarning OBJECT-TYPE
		SYNTAX	INTEGER {
			    heedWarning(1),
			    ignoreWarning(2)
		        }
		ACCESS	read-write
		STATUS	mandatory
		DESCRIPTION
			"The value of this variable determines how
			the SCP responds to a condition of too high
			or too low cabinet temperature, or both both
                        fans inoperative. If the value is heedWarning(1) 
                        the system will be shut down when the temperature 
                        goes outside the designed limits or both fans are 
                        inoperative. If the value is ignoreWarning(2),
			the system will continue to operate when either
                        of these conditions occur.


                        Setting this variable to ignoreWarning(2) allows
			the manager to cause a system that is too hot or
			too cold to continue to run. This variable will 
                        also allow both fans to be inoperative and still
                        allow the system to continue to run. Managers 
                        should note that doing so may be detrimental to 
                        the equipment. 

                        This object has a default value of heedWarning(1)." 
	::= { psc 8 }


-- The powerSupply subgroup

	rightPowerStatus OBJECT-TYPE
		SYNTAX	INTEGER {
			   notPresent(1),
			   okay(2),
		           fault(3)
			}
		ACCESS	read-only
		STATUS	mandatory
		DESCRIPTION
			"The status of the right power unit."
	::= { powerSupply 1 }


	rightPowerInputSource OBJECT-TYPE
		SYNTAX	INTEGER {
			   acLine(1),
			   dc48V(2),
			   none(3)
			}
		ACCESS	read-only
		STATUS	mandatory
		DESCRIPTION
			"The input source of the right power unit.

			A value of ACline(1) is returned if the power supply
			is connected to an AC line.

			A value of DC48V(2) is returned if the power supply is
			connected to a 48 volt DC (telecommunications) line.

			A value of none(3) is returned if the power unit is not
			present or not powered on.

			See the batteryUsing object to see if the battery or
			this power source is being used.
			"
	::= { powerSupply 2 }

	rightPowerOutputPower OBJECT-TYPE
		SYNTAX	INTEGER 
		ACCESS	read-only
		STATUS	mandatory
		DESCRIPTION
			"Output power of right power unit, in watts."
	::= { powerSupply 3 }

	leftPowerStatus OBJECT-TYPE
		SYNTAX	INTEGER {
			   notPresent(1),
			   okay(2),
		           fault(3)
			}
		ACCESS	read-only
		STATUS	mandatory
		DESCRIPTION
			"The status of the left power unit."
	::= { powerSupply 4 }


	leftPowerInputSource OBJECT-TYPE
		SYNTAX	INTEGER {
			   acLine(1),
			   dc48V(2),
			   none(3)
			}
		ACCESS	read-only
		STATUS	mandatory
		DESCRIPTION
			"The input source of the left power unit.

			A value of ACline(1) is returned if the power supply
			is connected to an AC line.

			A value of DC48V(2) is returned if the power supply is
			connected to a 48 volt DC (telecommunications) line.

			A value of none(3) is returned if the power unit is not
			present or not powered on.

			See the batteryUsing object to see if the battery or
			this power source is being used.
			"
	::= { powerSupply 5 }

	leftPowerOutputPower OBJECT-TYPE
		SYNTAX	INTEGER 
		ACCESS	read-only
		STATUS	mandatory
		DESCRIPTION
			"Output power of left power unit, in watts."
	::= { powerSupply 6 }

-- The slot subgroup

	slotNumber OBJECT-TYPE
		SYNTAX	INTEGER
		ACCESS	read-only
		STATUS	mandatory
		DESCRIPTION
			"The number of slots in the box."
	::= { slot 1 }

	scpSlot OBJECT-TYPE
		SYNTAX	INTEGER
		ACCESS	read-only
		STATUS	mandatory
		DESCRIPTION
			"Identifies the slot the Switch Control
	                 Processor (SCP) occupies. A value of 0 will 
                         be returned if an SCP has not been chosen."
	::= { slot 2 }


	slotTable OBJECT-TYPE
		SYNTAX	SEQUENCE OF SlotEntry
		ACCESS	not-accessible
		STATUS	mandatory
		DESCRIPTION
			"Describes the current configuration of the box."
	::= { slot 3 }


	slotEntry OBJECT-TYPE
		SYNTAX	SlotEntry
		ACCESS	not-accessible
		STATUS	mandatory
		DESCRIPTION
			"The description and status of the card
	                 plugged into the slot."
		INDEX	{ slotIndex }
	::= { slotTable 1 }

	SlotEntry ::= SEQUENCE {
	        slotIndex		INTEGER,
		slotCardStatus	        INTEGER,
		slotCardType	        INTEGER,
	        slotCardHwRev           DisplayString,
	        slotCardFwRev           DisplayString 
	}

	slotIndex OBJECT-TYPE
		SYNTAX	INTEGER
		ACCESS	read-only
		STATUS	mandatory
		DESCRIPTION
			"The slot number. Varies from 1 to slotNumber."
	::= { slotEntry 1 }


	slotCardStatus OBJECT-TYPE
		SYNTAX	INTEGER {
                           notPresent(1),
                           powerDown(2),        -- present but not poweredUp
                           powerUp(3),          -- present and poweredUp
                           powerDownThenUp(4),  -- for upgrading the FGL FW
			   fault(5),
			   revisionMismatch(6),
			   selfTestInProgress(7)
			}
		ACCESS	read-write
		STATUS	mandatory
		DESCRIPTION
			"The status of the card. If the value is
	                read as notPresent(1), then the entire entry 
	                should be considered invalid.

                        Writing a value of powerDown(2) will cause
		        the SCP to power down the card. Writing a
		        value of powerUp(3) will cause the SCP to
		        power up the card.  Writing a value of
			powerDownThenUp(4) will cause the SCP to power
                        cycle the line card.  Attempts to set any other
		        values will result in a badValue error.

			The clock and crossbar cards cannot be powered
			up or down through this object.  They are fundamental
			to the GIGAswitch's operation.  Unpopulated slots
			are notPresent(1), and can not be powered up or
			down.
			"
	::= { slotEntry 2 }


	slotCardType OBJECT-TYPE
		SYNTAX	INTEGER {
	                   other(1), -- none of the following
	                   fgl2(2),
	                   cbs36(3), 
	                   switchEngine(4),
	                   clockCard(5),
			   agl(6),
			   fgl4(7)
			}
		ACCESS	read-only
		STATUS	mandatory
		DESCRIPTION
			"The type of the Card."
	::= { slotEntry 3 }

	slotCardHwRev OBJECT-TYPE
		SYNTAX	DisplayString
		ACCESS	read-only
		STATUS	mandatory
		DESCRIPTION
			"The Hardware revision number of the card."
	::= { slotEntry 4 }

	slotCardFwRev OBJECT-TYPE
		SYNTAX	DisplayString
		ACCESS	read-only
		STATUS	mandatory
		DESCRIPTION
			"The Firmware revision number of the card."
	::= { slotEntry 5 }

-- The fan subgroup

	fanSpeed OBJECT-TYPE
		SYNTAX	INTEGER {
			   maximum(1),
			   normal(2)
			}
		ACCESS	read-write
		STATUS	mandatory
		DESCRIPTION
			" The speed of the fans.
		          Set this variable to maximum(1) for maximum
		          cooling where noise does not matter. 
                          Set this variable to normal(2) to cause 
                          fan speeds to be under temperature control."
	::= { fan 1 }


	rightFanStatus OBJECT-TYPE
		SYNTAX	INTEGER {
			   notPresent(1),
			   okay(2),
		           fault(3)
			}
		ACCESS	read-only
		STATUS	mandatory
		DESCRIPTION
			"The status of the right fan tray."
	::= { fan 2 }


	leftFanStatus OBJECT-TYPE
		SYNTAX	INTEGER {
			   notPresent(1),
			   okay(2),
		           fault(3)
			}
		ACCESS	read-only
		STATUS	mandatory
		DESCRIPTION
			"The status of the left fan tray."
	::= { fan 3 }

-- The battery subgroup

	-- There is no battery at FRS, so this object will read notPresent(1).

	batteryStatus OBJECT-TYPE
		SYNTAX	INTEGER {
			   notPresent(1),
			   okay(2),
		           fault(3)
			}
		ACCESS	read-only
		STATUS	mandatory
		DESCRIPTION
			"The status of the backup battery."
	::= { battery 1 }


	-- There is no battery at FRS, so this object is read-only and
	-- will read externalPower(1).
	-- When the battery is available, and this is made read-write,
	-- the same delicacies as batteryTest would apply.
	--		 Write this object to force the GIGAswitch to
	--               use power from the external power supplies,
	--               or from the backup battery.

	batteryUsing OBJECT-TYPE
		SYNTAX	INTEGER {
			   batteryPower(1),
			   externalPower(2)
			}
		ACCESS	read-only
		STATUS	mandatory
		DESCRIPTION
			"The source of power being used for the box.  The
			value batteryPower(2) indicates that the backup
			battery unit is being used to power the GIGAswitch.

			The external power line can be either AC or a
			48 volt DC telecommunications power line.
			"
	::= { battery 2 }

	batteryCharge OBJECT-TYPE
		SYNTAX	INTEGER {
			   fullyCharged(1),
			   okay(2),
		           low(3)
			}
		ACCESS	read-only
		STATUS	mandatory
		DESCRIPTION
			"The charge-level of the backup battery.
			Meaningful only if the battery is present."
	::= { battery 3 }


	-- There is no battery at FRS, so this object is read-only.

	batteryTest OBJECT-TYPE
		SYNTAX	INTEGER {
			   pass(1),
			   fail(2),
		           test(3)
			}
		ACCESS	read-only
		STATUS	mandatory
		DESCRIPTION
			"Only the value test(3) can be written.  Writes of
			other values are erroneous.

			This shows the result of the last battery test
			performed.  Testing the battery is risky, since the
			GIGAswitch is temporarily switched to run off the
			battery, and if the battery-backup system is not
			working properly, the GIGAswitch fails and restarts.

			Meaningful only if the battery is present.
			"
	::= { battery 4 }

-- The fppn subgroup
	
	-- Make the table read-write if ever introduce card types with more
	-- datalinks than switch ports, to allow new cards to be added while
	-- preserving utility of management memory contents.

	fppnTable OBJECT-TYPE
		SYNTAX	SEQUENCE OF FppnEntry
		ACCESS	not-accessible
		STATUS	mandatory
		DESCRIPTION
			"A list of front panel port number to MIB-II interface
			number mappings."
	::= { fppn 1 }


	fppnEntry OBJECT-TYPE
		SYNTAX	FppnEntry
		ACCESS	not-accessible
		STATUS	mandatory
		DESCRIPTION
			"Assigns the MIB-II interface ifIndex for a physical
			datalink (cable) connection to the box."
		INDEX	{ fppnSlotNumber, fppnPortOfThatSlot }
	::= { fppnTable 1 }

	FppnEntry ::= SEQUENCE {
		fppnSlotNumber		INTEGER,
		fppnPortOfThatSlot	INTEGER,
		fppnIfIndex		INTEGER,
		fppnBridgePortNumber	INTEGER
	}

	fppnSlotNumber OBJECT-TYPE
		SYNTAX	INTEGER
		ACCESS	read-only
		STATUS	mandatory
		DESCRIPTION
			"The 1-based slot number of the module."
	::= { fppnEntry 1 }

	fppnPortOfThatSlot OBJECT-TYPE
		SYNTAX	INTEGER
		ACCESS	read-only
		STATUS	mandatory
		DESCRIPTION
			"The 1-based media connection to the module."
	::= { fppnEntry 2 }

	fppnIfIndex OBJECT-TYPE
		SYNTAX	INTEGER
		ACCESS	read-only
		STATUS	mandatory
		DESCRIPTION
			"The assigned MIB-II ifIndex."
	::= { fppnEntry 3 }

	-- Save searching through the dot1dBasePortTable to find the
	-- dot1dBasePort for a dot1dBasePortIfIndex when plug a cable
	-- into the box and want to set a filter.

	fppnBridgePortNumber OBJECT-TYPE
		SYNTAX	INTEGER
		ACCESS	read-only
		STATUS	mandatory
		DESCRIPTION
			"The assigned Bridge MIB dot1dBasePort."
	::= { fppnEntry 4 }


-- The lineCard subgroup
	

	mPortTable OBJECT-TYPE
		SYNTAX	SEQUENCE OF MPortEntry
		ACCESS	not-accessible
		STATUS	mandatory
		DESCRIPTION
			"A list of mPort entries."
	::= { lineCard  1 }


	mPortEntry OBJECT-TYPE
		SYNTAX	MPortEntry
		ACCESS	not-accessible
		STATUS	mandatory
		DESCRIPTION
			"A collection of objects containing information
	                 for a given mPort MAC entity"
		INDEX	{ mPortSMTIndex, mPortMACIndex }
	::= { mPortTable 1 }

	MPortEntry ::= SEQUENCE {
            mPortSMTIndex		INTEGER,
            mPortMACIndex		INTEGER,
            mPortEnable			INTEGER
                 }


	mPortSMTIndex OBJECT-TYPE
            SYNTAX  INTEGER
            ACCESS  read-only
            STATUS  mandatory
            DESCRIPTION
                   "The value of the SMT index associated with this mPort MAC."
            ::= { mPortEntry 1 }

	mPortMACIndex OBJECT-TYPE
            SYNTAX  INTEGER
            ACCESS  read-only
            STATUS  mandatory
            DESCRIPTION
                   "The value of the MAC index associated with this mPort MAC."
            ::= { mPortEntry 2 }

	mPortEnable OBJECT-TYPE
            SYNTAX  INTEGER {
                              true(1),
                              false(2)
                            }
            ACCESS  read-write
            STATUS  mandatory
            DESCRIPTION
                   "When true, this link will be enabled to operate
		    in concentrator mode, i.e. mport."
            ::= { mPortEntry 3 }


-- the gigaBridge group

	flooding OBJECT IDENTIFIER ::= { gigaBridge 6 }

	floodUnknownUnicastRate OBJECT-TYPE
		SYNTAX	INTEGER
		ACCESS	read-write
		STATUS	mandatory
		DESCRIPTION
			"The maximum bytes-per-second bandwidth of packets
			multicast because the destination address was not yet
			learned by the bridge."
	::= { flooding 1 }

	floodMulticastRate OBJECT-TYPE
		SYNTAX	INTEGER
		ACCESS	read-write
		STATUS	mandatory
		DESCRIPTION
			"The maximum bytes-per-second bandwidth of packets
			multicast because the destination address is a
			multicast address."
	::= { flooding 2 }

	floodTable OBJECT-TYPE
		SYNTAX	SEQUENCE OF FloodEntry
		ACCESS	not-accessible
		STATUS	mandatory
		DESCRIPTION
			"Detailed view of the bridge flooding process."
	::= { flooding 3 }

	floodEntry OBJECT-TYPE
		SYNTAX	FloodEntry
		ACCESS	not-accessible
		STATUS	mandatory
		DESCRIPTION
			"Flooding state for a packet class and source."
		INDEX	{ floodQuotaQualifier, floodQuotaClass }
	::= { floodTable 1 }

	FloodEntry ::= SEQUENCE {
		floodQuotaQualifier		INTEGER,
		floodQuotaClass			INTEGER,
		floodBytesSent			INTEGER,
		floodPacketsSent		INTEGER,
		floodGeezers			INTEGER,
		floodLosers			INTEGER,
		floodHogs			INTEGER,
		floodSinglePathDiscards		INTEGER,
		floodPacketsFiltered		INTEGER,
		floodPacketsPurged		INTEGER,
		floodBytesPurged		INTEGER,
		floodLocalCopyPacketsDelivered	INTEGER,
		floodLocalCopyPacketsDiscarded	INTEGER
	}

	floodQuotaQualifier OBJECT-TYPE
		SYNTAX	INTEGER
		ACCESS	read-only
		STATUS	mandatory
		DESCRIPTION 
                        "The quota qualifier describes an incoming or outgoing
                        port.  It is a linear index to the port starting from
                        1.  If n is the quota qualifier for the first port of
                        a two port line card, the quota qualifier for the
                        second port is n + 1.  The clock card and the crossbar
                        have zero port, so the index must be skipped over those
                        slots.  This numbering scheme may be changed as we have
                        four port line cards."

	::= { floodEntry 1 }

	floodQuotaClass OBJECT-TYPE
		SYNTAX	INTEGER
		ACCESS	read-only
		STATUS	mandatory
		DESCRIPTION 
                        "The quota class describes the type of packet.
                        Four packet types are classified as follows:
                        1 - Unknown Destination Packets,
                        2 - Multicast Packets,
                        3 - IS-IS Packets,
                        4 - Bursty Control Packets"

	::= { floodEntry 2 }

	floodBytesSent OBJECT-TYPE
		SYNTAX	INTEGER
		ACCESS	read-only
		STATUS	mandatory
		DESCRIPTION
			"
			This object is the count of bytes in flooded packets.
			It does not include filtered packets or packets
			discarded due to buffer limitations. Each packet is
			counted once, regardless of the number of outbound
			links to which it was flooded.
			"
	::= { floodEntry 3 }

	floodPacketsSent OBJECT-TYPE
		SYNTAX	INTEGER
		ACCESS	read-only
		STATUS	mandatory
		DESCRIPTION 
                        "This object is the count of flooded packets.
                        It does not include filtered packets or packets
                        discarded due to buffer limitations. Each packet is
                        counted once, regardless of the number of outbound
                        links to which it was flooded.
                        "

	::= { floodEntry 4 }

	floodGeezers OBJECT-TYPE
		SYNTAX	INTEGER
		ACCESS	read-only
		STATUS	mandatory
		DESCRIPTION
			"
			This object is the count of packets that could not be
			flooded because they had remained in the SCP or in the
			inbound linecard too long.
			"
	::= { floodEntry 5 }

	floodLosers OBJECT-TYPE
		SYNTAX	INTEGER
		ACCESS	read-only
		STATUS	mandatory
		DESCRIPTION
			"
			This object is the count of packets discarded by the
			SCP flooding software (at the interrupt level) due to
			insufficient buffering.
			"
	::= { floodEntry 6 }

	floodHogs OBJECT-TYPE
		SYNTAX	INTEGER
		ACCESS	read-only
		STATUS	mandatory
		DESCRIPTION
			"
			This object is the count of packets for which buffer
			quota conversion to flooding software optimistic quotas
			failed.  This includes packets that were discarded as
			well as packets that were successfully flooded.
			"
	::= { floodEntry 7 }

	floodSinglePathDiscards OBJECT-TYPE
		SYNTAX	INTEGER
		ACCESS	read-only
		STATUS	mandatory
		DESCRIPTION
			"
			This object is the count of packets discarded to
			prevent packet misordering.  Certain protocol types
			are considered single-path and may not be delivered out
			of order.  If the Destination Address for a packet
			having a single-path protocol type is learned while
			the packet is buffered by the flooding software,
			the packet must be discarded (since line cards would
			have been directly forwarding packets using the learned
			address while packets received earlier were buffered on
			the SCP).
			"
	::= { floodEntry 8 }

	floodPacketsFiltered OBJECT-TYPE
		SYNTAX	INTEGER
		ACCESS	read-only
		STATUS	mandatory
		DESCRIPTION
			"
			This object is the count of packets discarded by the
			flooding software because user-configured filtering
			resulted in no allowed outbound transmit ports.
			"
	::= { floodEntry 9 }

	floodPacketsPurged OBJECT-TYPE
		SYNTAX	INTEGER
		ACCESS	read-only
		STATUS	mandatory
		DESCRIPTION
			"
			This object is the count of packets discarded due to
			the incoming link leaving FORWARDING state while they
			were buffered by flooding software.
			"
	::= { floodEntry 10 }

	floodBytesPurged OBJECT-TYPE
		SYNTAX	INTEGER
		ACCESS	read-only
		STATUS	mandatory
		DESCRIPTION
			"
			This object is the byte count in packets discarded due
			to the incoming link leaving FORWARDING state while
			they were buffered by flooding software.
			"
	::= { floodEntry 11 }

	floodLocalCopyPacketsDelivered OBJECT-TYPE
		SYNTAX	INTEGER
		ACCESS	read-only
		STATUS	mandatory
		DESCRIPTION
			"
			This object is the count of multicast packets addressed
			to software modules in the SCP that have been
			successfully delivered to those modules.
			"
	::= { floodEntry 12 }

	floodLocalCopyPacketsDiscarded OBJECT-TYPE
		SYNTAX	INTEGER
		ACCESS	read-only
		STATUS	mandatory
		DESCRIPTION
			"
			This object is the count of multicast packets addressed
			to software modules in the SCP that, because of buffer
			limitations, could not be delivered to those modules.
			"
	::= { floodEntry 13 }







-- gigaUpgradeSoftware group

	-- Upgrading software is a two-step process.  First the file is
	-- transfered, then it is copied to each destination.  This way,
	-- all the (FDDI) line cards can be updated with a single TFTP
	-- or MOP transfer.


	doTransfer  OBJECT IDENTIFIER ::= { gigaUpgradeSoftware 1 }
	useTransfer OBJECT IDENTIFIER ::= { gigaUpgradeSoftware 2 }

	tftpDestination OBJECT-TYPE
		SYNTAX	IpAddress
		ACCESS	read-write
		STATUS	mandatory
		DESCRIPTION "This object is the IP address of the host
			storing the file containing the software image. 

			The object may not be set until the last requested
			transfer succeeds or fails. So, before setting
			this object the user should verify that
			transferStatus does not have the value
			'requested' or 'inProgress'."
	::= { doTransfer 1 }

	mopDestination OBJECT-TYPE
		SYNTAX	OCTET STRING (SIZE(6))
		ACCESS	read-write
		STATUS	mandatory
		DESCRIPTION "This object is the 802 48-bit address of the host
			storing the file containing the software image.

			The object may not be set until the last requested
			transfer succeeds or fails. So, before setting this 
                        object, the user should verify that transferStatus
			does not have the value 'requested' or 'inProgress'.

			Both version 3 and version 4 of MOP are supported.

			If a unicast address is specified, the transfer will
			be from that host.  If the MOP multicast address
			ab-00-00-01-00-00 is used, the transfer will be from
			the first MOP server to respond, as usual."
	::= { doTransfer 2 }

	transferFileName OBJECT-TYPE
		SYNTAX	DisplayString
		ACCESS	read-write
		STATUS	mandatory
		DESCRIPTION "This object is the name of the file containing
			the software image.

			The object may not be set until the last requested
			transfer succeeds or fails. Before setting this 
                        object, the user should verify that transferStatus
			does not have the value 'requested' or 'inProgress'.

			Further, this object may not be set until the last
			requested copy succeeds or fails. Before setting 
			this object, the user should verify that copyStatus
			does not have the value 'requested' or 'inProgress'."
	::= { doTransfer 3 }


	-- UDP is unreliable and SNMP may therefore retransmit at the
	-- management station.  We do not distinguish retransmitted
	-- requests from errant requests to start a new transfer in the
	-- middle of an ongoing transfer.

	transferAction OBJECT-TYPE
		SYNTAX	INTEGER {
				none(1),
				doMOP(2),
				doTFTP(3)
			}
		ACCESS	read-write
		STATUS	mandatory
		DESCRIPTION "To initiate a transfer of a file from a
			server to the SCP, set this object.

			If transferFileName is non-empty, and
			mopDestination is non-zero, setting this
		   	object to doMOP(2) will cause a MOP
			'load' to be attempted. 

			If transferFileName is non-empty, and
			tftpDestination is non-zero, setting this
		      	object to doTFTP(3) will cause a TFTP
			'Get' to be attempted. 

			This object may not be set until the last
			requested transfer succeeds or fails, and the
			last requested copy succeeds or fails. So,
			before setting this object the user should
			verify that transferStatus does not have the
			values 'requested' or 'inProgress', and that
			copyStatus does not have the values
			'requested' or 'inProgress'.
			"
	::= { doTransfer 4 }


	transferStatus OBJECT-TYPE
		SYNTAX	INTEGER {
				none(1),
				requested(2),
				inProgress(3),
				failed(4),
				success(5),
				failedDueToCheckSum(6)
			}
		ACCESS	read-only
		STATUS	mandatory
		DESCRIPTION "This variable can be polled to determine when the
			transfer has completed.  Polling for completion allows
			other SNMP requests to be processed while the transfer
			is in progress (the SNMP is single-threaded)."
	::= { doTransfer 5 }

	transferSize OBJECT-TYPE
		SYNTAX	INTEGER
		ACCESS	read-only
		STATUS	mandatory
		DESCRIPTION "Size in bytes of the transfered file.  This object
			can be polled along with the transferStatus object to
			monitor the progress of the transfer."
	::= { doTransfer 6 }


	copyToSlot OBJECT-TYPE
		SYNTAX	INTEGER
		ACCESS	read-write
		STATUS	mandatory
		DESCRIPTION
			"The slot number of the card which is to be
			upgraded.

			The object may not be set until the last requested
			copy succeeds or fails."
	::= { useTransfer 1 }

	copyType OBJECT-TYPE
		SYNTAX	INTEGER {
				none(1),
				scp(2),
				fgl2(3),
				clock(4),
				powerSystemController(5),
				agl(6),
				fgl4(7)
			}
		ACCESS	read-only
		STATUS	mandatory
		DESCRIPTION
			"The type of the image.

			The object is set after a transfer succeeds or fails."
	::= { useTransfer 2 }



	-- UDP is unreliabile and SNMP may therefore retransmit at the
	-- management station.  We do not distinguish retransmitted
	-- requests from errant requests to start a new copy in the
	-- middle of an ongoing copy.

	copyAction OBJECT-TYPE
		SYNTAX	INTEGER {
				none(1),
				doUpgrade(2)
			}
		ACCESS	read-write
		STATUS	mandatory
		DESCRIPTION
			"To initiate a software upgrade of a card, set
			this object.

			If copyToSlot is non-zero, and
			copyType has a value other than
			'none', and transferStatus has the value
			'success', a software upgrade of the card is
			attempted. 

			The handler double-checks that the slot requires
			software of the expected type, and provides
			demultiplexing when multiple images may be sent to
			the same slot.  The power system controller is updated
			by sending its image to the clock card slot.

			The object may not be set until the last requested
			transfer succeeds, and the last requested copy
			succeeds or fails.

			Reading this object always returns the value
			none(1)."
	::= { useTransfer 3 }

	copyStatus OBJECT-TYPE
		SYNTAX	INTEGER {
				none(1),
				requested(2),
				inProgress(3),
				failed(4),
				success(5),
				failedDueToCardType(6),
				failedDueToHwRev(7),
				failedDueToFwRev(8),
				failedDueToBadImage(9)
			}
		ACCESS	read-only
		STATUS	mandatory
		DESCRIPTION "This variable can be polled to determine when the
			card upgrade has completed.  Polling for completion
			allows other SNMP requests to be processed while the
			copy is in progress (the SNMP is single-threaded)."
	::= { useTransfer 4 }


	deleteTransfer OBJECT-TYPE
		SYNTAX	INTEGER {
				exists(1),
				notExist(2)
			}
		ACCESS	read-write
		STATUS	mandatory
		DESCRIPTION
			"When read, this object indicates whether the result of
			a file transfer is still present.  The value exists
			indicates that the transferred file is present; the
			value notExist indicates that no file has been
			transferred or that it has been deleted.

			Writing the value exists is an error.  Writing the
			value notExist deletes the transferred file.

			The object may not be set until the last requested
			transfer succeeds or fails.  It may not be set while
			a copy is in progress, either."
	::= { gigaUpgradeSoftware 3 }


	arpTimingMechanism OBJECT IDENTIFIER ::= { gigaIP 1 }

	arpTimeoutInSeconds OBJECT-TYPE
		SYNTAX	INTEGER
		ACCESS  read-write
		STATUS  mandatory
		DESCRIPTION
			"The maximum amount of time an IP to LAN address
			translation will be used if it cannot be re-verified."
	::= { arpTimingMechanism 1 }

	arpPeriodBetweenRequests OBJECT-TYPE
		SYNTAX  INTEGER
		ACCESS  read-write
                STATUS  mandatory
		DESCRIPTION
			"The time, in seconds, between ARP requests that
			are used to verify or to discover an IP to LAN address 
			translation."
	::= { arpTimingMechanism 2 }

	arpRequestRetries OBJECT-TYPE
                SYNTAX  INTEGER
                ACCESS  read-write
                STATUS  mandatory
                DESCRIPTION
			"The number of times ARP requests are used to verify
			or to discover an IP to LAN address translation."
	::= { arpTimingMechanism 3 }

	arpControlParams OBJECT IDENTIFIER ::= { gigaIP 3 }

	arpAgent OBJECT-TYPE
        	SYNTAX  INTEGER {
                        	true(1),
                        	false(2)
                	}
        	ACCESS  read-write
        	STATUS  mandatory
        	DESCRIPTION "
			When true, the GIGAswitch will service broadcast
			ARP requests from its ARP cache.

			When false, Broadcast ARP frames are flooded.
			"
	::= { arpControlParams 1 }

	arpStatisticalCounters OBJECT IDENTIFIER ::= { gigaIP 4 }

	arpStatisticalTable OBJECT-TYPE
        	SYNTAX  SEQUENCE OF ArpStatisticalEntry
        	ACCESS  not-accessible
        	STATUS  mandatory
        	DESCRIPTION "
			This table stores ARP counters.
			"
	::= { arpStatisticalCounters 1 }

	arpStatisticalEntry OBJECT-TYPE
        	SYNTAX  ArpStatisticalEntry
        	ACCESS  not-accessible
        	STATUS  mandatory
        	DESCRIPTION "
			Information about the ARP statistical table is stored.
			"
		INDEX { arpStatisticalIfIndex }
	::= { arpStatisticalTable 1 }

	ArpStatisticalEntry ::=
		SEQUENCE {
			arpStatisticalIfIndex	INTEGER,
			arpUnicastReceived	Counter,
			arpBroadcastReceived	Counter,
			arpRepliesTransmitted	Counter,
			arpFramesFlooded	Counter,
			arpFramesDiscarded	Counter	
		}

	arpStatisticalIfIndex	OBJECT-TYPE
        	SYNTAX  INTEGER
        	ACCESS  read-only
        	STATUS  mandatory
        	DESCRIPTION "
               		Identifies the Interface.  The value of this object is
               		the same as the ifIndex, defined in MIB-II, for this
               		interface.
			"
        ::= { arpStatisticalEntry 1 }

	arpUnicastReceived	OBJECT-TYPE
		SYNTAX  Counter
		ACCESS  read-only
		STATUS  mandatory
		DESCRIPTION "
			Unicast ARP requests received on this port.
			"
	::= { arpStatisticalEntry 2 }
		
	arpBroadcastReceived OBJECT-TYPE
		SYNTAX  Counter
		ACCESS  read-only
		STATUS  mandatory
		DESCRIPTION "
			Broadcast ARP requests received on this port.
			"
	::= { arpStatisticalEntry 3 }
		
	arpRepliesTransmitted OBJECT-TYPE
		SYNTAX  Counter
		ACCESS  read-only
		STATUS  mandatory
		DESCRIPTION "
			ARP replies transmitted on this port.
			"
	::= { arpStatisticalEntry 4 }
		
	arpFramesFlooded OBJECT-TYPE
		SYNTAX  Counter
		ACCESS  read-only
		STATUS  mandatory
		DESCRIPTION "
			ARP frames received on this port that required
			flooding while acting as an ARP agent.
			"
	::= { arpStatisticalEntry 5 }
		
	arpFramesDiscarded OBJECT-TYPE
		SYNTAX  Counter
		ACCESS  read-only
		STATUS  mandatory
		DESCRIPTION "
			ARP frames received on this port that were discarded
			due to protocol errors.
			"
	::= { arpStatisticalEntry 6 }

	snmpParameters OBJECT IDENTIFIER ::= { gigaIP 2 }

        snmpDuplicateDiscardInterval OBJECT-TYPE
                SYNTAX  INTEGER
                ACCESS  read-write
                STATUS  mandatory
                DESCRIPTION "
                        If duplicated snmp messages arrive within this
                        interval, all but the first one will be discarded.

                        The unit is a hundredth of second.
                        "
        ::= { snmpParameters 1 }


	gigaStp  OBJECT IDENTIFIER ::= { gigaBridge 8 }


-- The gigaStp subgroup


        gigaStpPortTable OBJECT-TYPE
                SYNTAX  SEQUENCE OF GigaStpPortEntry
                ACCESS  not-accessible
                STATUS  mandatory
                DESCRIPTION 
                        " A list of  gigaStp entries "
        ::= { gigaStp 1 }

        gigaStpPortEntry OBJECT-TYPE
                SYNTAX  GigaStpPortEntry
                ACCESS  not-accessible
                STATUS  mandatory
                DESCRIPTION "
			A collection of objects containing information
			for a given StpPort
			"
                INDEX   { gigaStpPortIfIndex }
        ::= { gigaStpPortTable 1 }

        GigaStpPortEntry ::= SEQUENCE {
            gigaStpPortIfIndex              INTEGER,
            gigaStpPortSpanningTreeEnable   INTEGER
                 }

        gigaStpPortIfIndex OBJECT-TYPE
            SYNTAX  INTEGER
            ACCESS  read-only
            STATUS  mandatory
            DESCRIPTION
                   "The value of the interface associated with this
                    spanning tree port."
            ::= { gigaStpPortEntry 1 }

        gigaStpPortSpanningTreeEnable OBJECT-TYPE
            SYNTAX  INTEGER {
                              true(1),
                              false(2)
                            }
            ACCESS  read-write
            STATUS  mandatory
            DESCRIPTION
                   "When true, this interface will be enabled to operate
                    as part of the spanning tree."
            ::= { gigaStpPortEntry 2 }

	translationTableParams  OBJECT IDENTIFIER ::= { gigaBridge 9 }

        ttSize OBJECT-TYPE
                SYNTAX  INTEGER 
                ACCESS  read-only
                STATUS  mandatory
                DESCRIPTION "
			The number of entries in the tables used to store
			learned network addresses.
                        "
        ::= { translationTableParams 1 }



        --
        -- This MIB defines the AGL specific objects required 
        -- for module operation within the Gigaswitch
        --

        agl             OBJECT IDENTIFIER ::= { gigaswitch 4 }

        -- groups in the AGL2 MIB module

        aglConfig       OBJECT IDENTIFIER ::= { agl 1 }
        aglSonet        OBJECT IDENTIFIER ::= { agl 2 }
        aglDS3E3        OBJECT IDENTIFIER ::= { agl 3 }
        aglAtm          OBJECT IDENTIFIER ::= { agl 4 }

        -- aglSNP          OBJECT IDENTIFIER ::= { agl 5 }

        --
        -- The AGL Configuration Group
        --
        -- Implementation of this group is mandatory
        --

        aglInterfaceConfTable   OBJECT-TYPE
                SYNTAX          SEQUENCE OF AglInterfaceConfEntry
                ACCESS          not-accessible
                STATUS          mandatory
                DESCRIPTION
                        "
                        This table contains the AGL specific interface 
                        configuration parameters, one entry per ATM 
                        interface port.
                        "
                ::= { aglConfig 1 }

        aglInterfaceConfEntry   OBJECT-TYPE
                SYNTAX          AglInterfaceConfEntry
                ACCESS          not-accessible
                STATUS          mandatory
                DESCRIPTION
                        "
                        This list contains ATM interface configuration
                        parameters and state variables.
                        "
                INDEX { aglInterfaceIndex }

                ::= { aglInterfaceConfTable  1 }

        AglInterfaceConfEntry   ::= SEQUENCE  
		{
                aglInterfaceIndex                       INTEGER,
                aglInterfacePhyType                     INTEGER,
                aglInterfaceTrafficRateGranularity      INTEGER
                }

                
        aglInterfaceIndex       OBJECT-TYPE
                SYNTAX          INTEGER
                ACCESS          read-only
                STATUS          mandatory
                DESCRIPTION
                        "
                        The value of this object identifies the AGL port
                        interface for which this entry contains management 
                        information.
                        "
                ::= { aglInterfaceConfEntry 1 }


        aglInterfacePhyType  OBJECT-TYPE
                SYNTAX       INTEGER  {
                                        sts3cStm1(1),
                                        ds3e3(2),
					unKnown(3)
                                      }
                ACCESS          read-only
                STATUS          mandatory
                DESCRIPTION
                        "
                        Indicates the type of physical interface used on the 
                        ATM port. Two physical layer types are supported:
                                        1. STS3c/STM1
                                        2. DS3/E3

			The type is unknown if the port is not present or
			its physical layer type is not known.
                        "
                ::= { aglInterfaceConfEntry 2 }

        aglInterfaceTrafficRateGranularity      OBJECT-TYPE
                SYNTAX          INTEGER
                ACCESS          read-only
                STATUS          mandatory
                DESCRIPTION
                        "
                        Indicates the granularity in cell/s for assigning
                        peak, average and minimum guaranteed rates for 
                        traffic shaped circuits on the AGL port. This value
                        also represents the minimum rate in cells/s that can
                        be assigned to a circuit. The rates subscribed to in 
                        the aglVCConnectionTable will be set to a multiple
			of this rate.
                        "
                ::= { aglInterfaceConfEntry 3 }



        --
        -- The AGL Sonet Group
        --
        -- Implementation of this group is mandatory
        --

        aglInterfaceSonetTable  OBJECT-TYPE
                SYNTAX          SEQUENCE OF AglInterfaceSonetEntry
                ACCESS          not-accessible
                STATUS          mandatory
                DESCRIPTION
                        "
                        This table contains the AGL specific interface 
                        configuration parameters for the SONET/SDH physical
                        layer.
                        "
                 ::= { aglSonet 1 }

        aglInterfaceSonetEntry  OBJECT-TYPE
                SYNTAX          AglInterfaceSonetEntry
                ACCESS          not-accessible
                STATUS          mandatory
                DESCRIPTION
                        "
                        This list contains SONET/SDH interface configuration
                        parameters and state variables.
                        "
                INDEX { aglInterfaceSonetIndex }

                ::= { aglInterfaceSonetTable  1 }

        AglInterfaceSonetEntry  ::= SEQUENCE  {
                aglInterfaceSonetIndex       INTEGER,
                aglInterfaceSonetMode        INTEGER,
                aglInterfaceSonetTiming      INTEGER
                }


        aglInterfaceSonetIndex  OBJECT-TYPE
                SYNTAX          INTEGER
                ACCESS          read-only
                STATUS          mandatory
                DESCRIPTION
                        "
                        The value of this object identifies the AGL 
                        port interface for which this entry contains
                        management information and is the same as 
                        aglInterfaceIndex.
                        "
                 ::= { aglInterfaceSonetEntry 1 }

        aglInterfaceSonetMode   OBJECT-TYPE
                SYNTAX       INTEGER  {
                                        sonetSTS3c(1),
                                        sdhSTM1(2)
                                      }
                ACCESS       read-write
                STATUS       mandatory
                DESCRIPTION
                        "
                        Specifies whether the PHY operates in SONET STS-3c
                        or SDH STM-1 mode. The following code points are 
                        used:
                                1       SONET STS-3c
                                2       SDH STM-1
                        "
                ::= { aglInterfaceSonetEntry 2 }

        aglInterfaceSonetTiming         OBJECT-TYPE
                SYNTAX       INTEGER  {
                                        loopTiming(1),
                                        localTiming(2)
                                      }
                ACCESS       read-write
                STATUS       mandatory
                DESCRIPTION
                        "
                        Specifies whether the PHY operates in loop-timing
                        or local-timing mode. In loop-timing, the recovered
                        clock from the receive signal is used directly to 
                        time transmit data. Hence, the PHY is synchronized 
                        to the far-end transmitter. In local timing, transmit 
                        data is timed from a local oscillator of frequency 
                        155.52 MHz (20ppm). The following code points are 
                        used:
                                1       loop-timing
                                2       local-timing
                        "
                ::= { aglInterfaceSonetEntry 3 }

        --
        -- The AGL DS3/E3 Group
        --
        -- Implementation of this group is mandatory
        --

        aglInterfaceDS3E3Table  OBJECT-TYPE
                SYNTAX          SEQUENCE OF AglInterfaceDS3E3Entry
                ACCESS          not-accessible
                STATUS          mandatory
                DESCRIPTION
                        "
                        This table contains the AGL specific interface
                        configuration parameters for the DS3/E3 physical
                        layer.
                        "
                 ::= { aglDS3E3 1 }

        aglInterfaceDS3E3Entry  OBJECT-TYPE
                SYNTAX          AglInterfaceDS3E3Entry
                ACCESS          not-accessible
                STATUS          mandatory
                DESCRIPTION
                        "
                        This list contains DS3/E3 interface configuration
                        parameters and state variables.
                        "
                INDEX { aglInterfaceDS3E3Index }

                ::= { aglInterfaceDS3E3Table  1 }

        AglInterfaceDS3E3Entry  ::= SEQUENCE  {
                aglInterfaceDS3E3Index       INTEGER,
                aglInterfaceDS3E3Mode        INTEGER,
                aglInterfaceDS3E3Plcp        INTEGER
                }


        aglInterfaceDS3E3Index  OBJECT-TYPE
                SYNTAX          INTEGER
                ACCESS          read-only
                STATUS          mandatory
                DESCRIPTION
                        "
                        The value of this object identifies the AGL
                        port interface for which this entry contains
                        management information and is the same as
                        aglInterfaceIndex.
                        "
                 ::= { aglInterfaceDS3E3Entry 1 }

        aglInterfaceDS3E3Mode   OBJECT-TYPE
                SYNTAX       INTEGER  {
                                        low-power(1),
                                        high-power(2)
                                      }
                ACCESS       read-write
                STATUS       mandatory
                DESCRIPTION
                        "
                        Specifies whether the DS3/E3 PHY operates in low
                        power mode for short distances or high power mode
                        for longer distances. The following code points are
                        used:
                                1       low-power
                                2       high-power
                        "
                ::= { aglInterfaceDS3E3Entry 2 }

        aglInterfaceDS3E3Plcp   OBJECT-TYPE
                SYNTAX       INTEGER  {
                                        enable(1),
                                        disable(2)
                                      }
                ACCESS       read-write
                STATUS       mandatory
                DESCRIPTION
                        "
                        Specifies whether ATM cells may be mapped into
			the DS3 PLCP.  In the enabled mode, PLCP framing
			and timing is applied to each ATM cell.
                        "
                ::= { aglInterfaceDS3E3Entry 3 }

        --
        -- The AGL ATM Group
        --
        -- Implementation of this group is mandatory
        --
        -- The AglVCConnectionTable allows a network manager to setup
        -- single-port bidirectional circuits or dual-port bidirectional 
        -- circuits. A single-port circuit terminates at that port, 
        -- whereas a dual-port circuit establishes a connection through
        -- the GIGAswitch between the two ports (A and B). If a single-port
        -- connection is to be established, the user simply enters zero
        -- values for port B parameters below.
        --
        --                          GIGAswitch
        --                        --------------
        --                       |              |
        --          Rx --------->| PortA        |
        --          Tx <---------|              |
        --                       |              |
        --                       |              |
        --                       |        PortB |--------> Tx
        --                       |              |<-------- Rx
        --                       |              |
        --                        --------------
        --                              

        aglVCConnectionTable    OBJECT-TYPE
                SYNTAX  SEQUENCE OF AglVCConnectionTableEntry
                ACCESS  not-accessible
                STATUS  mandatory
                DESCRIPTION
                        "
                        This table contains AGL ATM VCC configuration 
                        and performance parameters and state variables.
                        Each entry represents a bidirectional traffic 
                        flow.
                        "
                ::= { aglAtm 1 }
        
        aglVCConnectionTableEntry    OBJECT-TYPE
                SYNTAX  AglVCConnectionTableEntry
                ACCESS  not-accessible
                STATUS  mandatory
                DESCRIPTION
                        "
                        A bidirectional circuit.
                        "
                INDEX { aglVCConnectionPortA, aglVCConnectionPortAVpi,
                        aglVCConnectionPortAVci, aglVCConnectionPortB,
                        aglVCConnectionPortBVpi, aglVCConnectionPortBVci} 

                ::= { aglVCConnectionTable 1 }

        AglVCConnectionTableEntry ::= SEQUENCE {
                aglVCConnectionPortA                            INTEGER,
                aglVCConnectionPortAVpi                         INTEGER,
                aglVCConnectionPortAVci                         INTEGER,
                aglVCConnectionPortB                            INTEGER,
                aglVCConnectionPortBVpi                         INTEGER,
                aglVCConnectionPortBVci                         INTEGER,
                aglVCConnectionTableEntryStatus                 INTEGER,
                aglVCConnectionTrafficType                      INTEGER,
                aglVCConnectionAALType                          INTEGER,
                aglVCConnectionOperStatus                       INTEGER,
                aglVCConnectionAdminStatus                      INTEGER,
                aglVCConnectionTrafficShaperPeakRate            INTEGER,
                aglVCConnectionTrafficShaperAvgRate             INTEGER,
                aglVCConnectionTrafficShaperMinGuaranteedRate   INTEGER,
                aglVCConnectionTrafficShaperPriority            INTEGER
                }

        aglVCConnectionPortA    OBJECT-TYPE
                SYNTAX  INTEGER
                ACCESS  read-only
                STATUS  mandatory
                DESCRIPTION
                        "
                        The value of this object identifies the AGL
                        ATM port A of the VCC segment for FDDI-bridged
                        and ATM-to-ATM circuit types.
                        "
                 ::= { aglVCConnectionTableEntry 1 }

        aglVCConnectionPortAVpi       OBJECT-TYPE
                SYNTAX  INTEGER  (0..255)
                ACCESS  read-only
                STATUS  mandatory
                DESCRIPTION
                        "
                        The VPI value at port A for the bidirectional 
                        circuit. The maximum VPI value cannot exceed 
                        the number supported by the atmInterfaceMaxVpiBits 
                        at AGL ATM port A. This value is used for both 
                        transmit and receive VPIs 
                        "
                 ::= { aglVCConnectionTableEntry 2 }

        aglVCConnectionPortAVci       OBJECT-TYPE
                SYNTAX  INTEGER  (32..65535)
                ACCESS  read-only
                STATUS  mandatory
                DESCRIPTION
                        "
                        The VCI value at the port A for the
                        bidirectional circuit. The VCI values from 0 
                        to 31 are reserved.  The maximum VCI value
                        cannot exceed the number supported by the 
                        atmInterfaceMaxVciBits specified for the AGL 
                        ATM port A. This value is used for both 
                        transmit and receive VCIs 
                        "
                 ::= {  aglVCConnectionTableEntry 3 }


        aglVCConnectionPortB    OBJECT-TYPE
                SYNTAX  INTEGER
                ACCESS  read-only
                STATUS  mandatory
                DESCRIPTION
                        "
                        The value of this object identifies the AGL
                        ATM port B of the VCC segment for ATM-to-ATM
                        circuit types. For FDDI-bridged circuit types 
                        this value should be zero. 
                        "
                 ::= { aglVCConnectionTableEntry 4 }

        aglVCConnectionPortBVpi       OBJECT-TYPE
                SYNTAX  INTEGER  (0..255)
                ACCESS  read-only
                STATUS  mandatory
                DESCRIPTION
                        "
                        The VPI value at port B for the bidirectional 
                        ATM-to-ATM circuit.  The maximum VPI value 
                        cannot exceed the number supported by the 
                        atmInterfaceMaxVpiBits at AGL ATM port B.
                        This value is used for both transmit and receive 
                        VPIs. For other circuit types this value should be 
                        zero.
                        "
                 ::= { aglVCConnectionTableEntry 5 }

        aglVCConnectionPortBVci       OBJECT-TYPE
                SYNTAX  INTEGER  (32..65535)
                ACCESS  read-only
                STATUS  mandatory
                DESCRIPTION
                        "
                        The VCI value at the port B for the
                        bidirectional ATM-to-ATM circuit. The VCI values 
                        from 0 to 31 are reserved.  The maximum VCI value
                        cannot exceed the number supported by the 
                        atmInterfaceMaxVciBits specified for the AGL 
                        ATM port B. This value is used for both transmit 
                        and receive VCIs. For other circuit types this value 
                        should be zero.
                        "
                 ::= {  aglVCConnectionTableEntry 6 }

        aglVCConnectionTableEntryStatus OBJECT-TYPE
                SYNTAX  INTEGER {
                                   create(1),
                                   delete(2)
                                }
                ACCESS  read-write
                STATUS  mandatory
                DESCRIPTION
                        "
                        The status column used for creating, 
                        and deleting bidirectional circuit 
                        entries in the agl virtual channel 
                        connection table.
                        "
                 ::= { aglVCConnectionTableEntry 7 }

        aglVCConnectionTrafficType      OBJECT-TYPE
                SYNTAX   INTEGER  {
                                    FDDI-bridged(1),
                                    ATM-to-ATM(2)
                                  }
                ACCESS  read-write
                STATUS  mandatory
                DESCRIPTION
                        "
                        The value of this object identifies the circuit
                        type and characteristics of a particular circuit.
                        There are two types of connections supported:
                                1. FDDI-bridged
                                2. ATM-to-ATM
                        An FDDI-bridged circuit carries all bridged FDDI
                        traffic on AGL ATM port A. No information is required
                        to be entered for Port B. Only one bridged FDDI 
                        circuit per AGL ATM port is supported. The packet 
                        format on this circuit is VC based multiplexed 
                        bridged FDDI as per RFC 1483.
                        
                        An ATM-to-ATM circuit carries arbitrary packet types
                        between circuits specified on Port A and Port B of
                        the GIGAswitch. Multiple ATM-to-ATM circuits are 
                        supported per AGL ATM port.
                        "
                 ::= { aglVCConnectionTableEntry 8 }

        aglVCConnectionAALType  OBJECT-TYPE
                SYNTAX   INTEGER  {
                                    aal34(1),
                                    aal5(2) 
                                  }
                ACCESS  read-write
                STATUS  mandatory
                DESCRIPTION
                        "
                        The value of this object identifies the AAL type 
                        that should be used on a particular circuit.
                        "
                 ::= { aglVCConnectionTableEntry 9 }


        aglVCConnectionOperStatus       OBJECT-TYPE
                SYNTAX   INTEGER  { 
                                    up(1),
                                    down(2),
				    unknown(3) 
                                  }
                ACCESS  read-only
                STATUS  mandatory
                DESCRIPTION
                        "
                        This object indicates the operational status
                        of the VCC, i.e., whether the managed VCC
                        segment is up or down. In the down state,
                        no cells can get across this VCC segment.
			The status is unknown if the OAM is disabled.
                        "
                ::= { aglVCConnectionTableEntry 10 }

        aglVCConnectionAdminStatus    OBJECT-TYPE
                SYNTAX   INTEGER  { 
                                    enable(1),
                                    disable(2) 
                                  }
                ACCESS  read-write
                STATUS  mandatory
                DESCRIPTION
                        "
                        This object indicates the desired status
                        of the VCC, i.e., whether the managed VCC
                        segment is enabled or disabled. In the disabled
                        state, no cells can be passed across this VCC
                        segment.
                        "
                 ::= { aglVCConnectionTableEntry 11 }

        aglVCConnectionTrafficShaperPeakRate    OBJECT-TYPE
                SYNTAX  INTEGER
                ACCESS  read-write
                STATUS  mandatory
                DESCRIPTION
                        "
                        The value of this object specifies the peak rate in
                        cells/s that should be used on a particular circuit.
                        The peak rate will be set to a multiple of the 
                        aglInterfaceTrafficRateGranularity close to the
			user specified input.
                        "
                ::= { aglVCConnectionTableEntry 12 }

        aglVCConnectionTrafficShaperAvgRate     OBJECT-TYPE
                SYNTAX  INTEGER
                ACCESS  read-write
                STATUS  mandatory
                DESCRIPTION
                        "
                        The value of this object specifies the average 
                        (sustained) rate in cells/s that should be used 
                        on a particular circuit.  The average rate must be 
                        less than or equal to the peak rate and it will be 
                        set to a multiple of the aglInterfaceTrafficRate-
			Granularity close to the user specified input.
                        " 
                ::= { aglVCConnectionTableEntry 13 }

        aglVCConnectionTrafficShaperMinGuaranteedRate   OBJECT-TYPE
                SYNTAX  INTEGER
                ACCESS  read-write
                STATUS  mandatory
                DESCRIPTION
                        "
                        The value of this object specifies the minimum 
                        guaranteed rate in cells/s that should be used 
                        on a particular circuit.  For VBR traffic AGL 
                        allows the possibility of overbooking link bandwidth 
                        (up to 1200%) to achive statistical multiplexing. 
                        This parameter specifies the minimum peak bandwidth 
                        that you want to guarantee to the circuit. The 
                        minimum guaranteed rate must be less than or equal 
                        to the peak rate and it will be set to a multiple 
			of the aglInterfaceTrafficRateGranularity close
			to the user specified input.
                        "
                ::= { aglVCConnectionTableEntry 14 }

        aglVCConnectionTrafficShaperPriority    OBJECT-TYPE
                SYNTAX  INTEGER (1..12)
                ACCESS  read-write
                STATUS  mandatory
                DESCRIPTION
                        "
                        The value of this object specifies the priority which 
                        should be given to this circuit in assigning 
                        opportunistic bandwidth that arises from AGL's 
                        bandwidth overbooking policy.
                        "
                ::= { aglVCConnectionTableEntry 15 }

	--
	-- The AGL specific ATM Group
	-- Implementation of this group is mandatory
	--

        aglInterfaceATMTable	OBJECT-TYPE
                SYNTAX  SEQUENCE OF AglInterfaceATMTableEntry
                ACCESS  not-accessible
                STATUS  mandatory
                DESCRIPTION
                        "
                        This table contains AGL ATM interface specific
			settable parameters.
                        "
                ::= { aglAtm 2 }

        aglInterfaceATMTableEntry	OBJECT-TYPE
                SYNTAX  AglInterfaceATMTableEntry
                ACCESS  not-accessible
                STATUS  mandatory
                DESCRIPTION
                        "
                        The list of settable parameters.
                        "
                INDEX { aglInterfaceATMIndex }

                ::= { aglInterfaceATMTable 1 }

        AglInterfaceATMTableEntry	::= SEQUENCE  {
                aglInterfaceATMIndex			INTEGER,
                aglInterfaceATMScrambeStatus		INTEGER,
                aglInterfaceATMOAMStatus		INTEGER
                }

        aglInterfaceATMIndex       OBJECT-TYPE
                SYNTAX          INTEGER
                ACCESS          read-write
                STATUS          mandatory
                DESCRIPTION
                        "
                        The value of this object identifies the AGL port
                        interface for which this entry contains management
                        information and is the same as aglInterfaceIndex.
                        "
                ::= { aglInterfaceATMTableEntry 1 }

        aglInterfaceATMScrambeStatus	OBJECT-TYPE
                SYNTAX   INTEGER  {
                                    enable(1),
                                    disable(2)
                                  }
                ACCESS          read-write
                STATUS          mandatory
                DESCRIPTION
                        "
                        This object indicates the desired status
                        of the cell scramble module.  In the enabled
			state, outgoing cells are scrambed and input
			cells are descrambled.
                        "
                ::= { aglInterfaceATMTableEntry 2 }

        aglInterfaceATMOAMStatus	OBJECT-TYPE
                SYNTAX   INTEGER  {
                                    enable(1),
                                    disable(2)
                                  }
                ACCESS          read-write
                STATUS          mandatory
                DESCRIPTION
                        "
                        This object indicates the desired status
                        of the OAM module in the default circuit.  
			In the enabled state, normal OAM cells 
			are exchanged between the peers.
                        "
                ::= { aglInterfaceATMTableEntry 3 }



	--
	-- aglSNP branch snapshots the objects that are expected to be evolved and currently
	-- located under the experimental subtree.  Some objects were taken out from the
	-- experimental ATM and SONET MIBs and prefixed with agl.  The objects under this
	-- branch may be deprecated once the standard committee finalize the objects.
	--

	-- aglatmMIB OBJECT IDENTIFIER ::= { aglSNP 1 }

	aglatmMIB OBJECT IDENTIFIER ::= { gigaswitch 5 }

	aglatmMIBObjects OBJECT IDENTIFIER ::= { aglatmMIB  1 }

	aglatmInterfaceTrafficEnforcementTypes OBJECT IDENTIFIER ::= { aglatmMIBObjects  1 }

	aglatmInterfaceNoTrafficEnforcement OBJECT-TYPE
    		SYNTAX  OBJECT IDENTIFIER
    		ACCESS  read-only
    		STATUS  mandatory
    		DESCRIPTION
           		"This identifies the no ATM traffic enforcement type."
    	::= { aglatmInterfaceTrafficEnforcementTypes  1 }

	aglatmInterfaceTrafficEnforcementType1 OBJECT-TYPE
    		SYNTAX  OBJECT IDENTIFIER
    		ACCESS  read-only
    		STATUS  mandatory
    		DESCRIPTION
           		"This identifies the ATM traffic enforcement type is 1.
                       	For type 1 traffic enforcement, parameter 1
                       	specifies CLP=0+1 peak traffic.  Parameters 2, 3, 4
                       	and 5 are not used. The peak rate is measured
                       	in cells per second."
    	::= { aglatmInterfaceTrafficEnforcementTypes  2 }

	aglatmInterfaceTrafficEnforcementType2 OBJECT-TYPE
    		SYNTAX  OBJECT IDENTIFIER
    		ACCESS  read-only
    		STATUS  mandatory
    		DESCRIPTION
           		"This identifies the ATM traffic enforcement type is 2.
                       	For type 2 traffic enforcement, parameter 1
                       	specifies CLP=0 peak traffic and parameter
                       	2 specifies CLP=0+1 peak traffic.  Parameters 3, 4,
                       	and 5 are not used. The peak rate is measured
                       	in cells per second."
    	::= { aglatmInterfaceTrafficEnforcementTypes  3 }

	aglatmInterfaceTrafficEnforcementType3 OBJECT-TYPE
    		SYNTAX  OBJECT IDENTIFIER
    		ACCESS  read-only
    		STATUS  mandatory
    		DESCRIPTION
           		"This identifies the ATM traffic enforcement type is 3.
                       	For type 3 traffic enforcement, parameter 1
                       	specifies CLP=0+1 peak traffic, parameter
                       	2 specifies CLP=0 sustained rate, and parameter 3
                       	specifies CLP=0 maximum burst size.  Parameters 4
                       	and 5 are not used. The peak rate is measured
                       	in cells per second. The sustained rate is measured
                       	in cells per second and burst size is measured in cells."
    	::= { aglatmInterfaceTrafficEnforcementTypes  4 }

	aglatmInterfaceTrafficEnforcementType4 OBJECT-TYPE
    		SYNTAX  OBJECT IDENTIFIER
    		ACCESS  read-only
    		STATUS  mandatory
    		DESCRIPTION
           		"This identifies the ATM traffic enforcement type is 4.
                       	For type 4 traffic enforcement, parameter 1
                       	specifies CLP=0 peak traffic, parameter
                       	2 specifies CLP=0+1 peak traffic, and parameter 3
                       	specifies tagging (e.g., a value 1 may be
                       	used to indicate tagging).  Parameters 4
                       	and 5 are not used. The peak rate is measured
                       	in cells per second."
    	::= { aglatmInterfaceTrafficEnforcementTypes  5 }

	aglatmInterfaceTrafficEnforcementType5 OBJECT-TYPE
    		SYNTAX  OBJECT IDENTIFIER
    		ACCESS  read-only
    		STATUS  mandatory
    		DESCRIPTION
           		"This identifies the ATM traffic enforcement type is 5.
                       	For type 5 traffic enforcement, parameter 1
                       	specifies CLP=0+1 peak traffic, parameter
                       	2 specifies CLP=0 sustained rate, parameter 3
                       	specifies CLP=0 maximum burst size, and parameter
                       	4 specifies tagging (e.g., a value 1 may be
                       	used to indicate tagging).  Parameter
                       	5 is not used."
    	::= { aglatmInterfaceTrafficEnforcementTypes  6 }

	aglatmInterfaceTrafficEnforcementType6 OBJECT-TYPE
    		SYNTAX  OBJECT IDENTIFIER
    		ACCESS  read-only
    		STATUS  mandatory
    		DESCRIPTION
           		"This identifies the ATM traffic enforcement type is 6.
                       	For type 6 traffic enforcement, parameter 1
                       	specifies CLP=0+1 peak traffic, parameter
                       	2 specifies CLP=0+1 sustained rate, and parameter 3
                       	specifies CLP=0+1 maximum burst size.
                       	Parameters 4 and 5 are not used."
    	::= { aglatmInterfaceTrafficEnforcementTypes  7 }

	aglatmInterfaceTrafficEnforcementType7 OBJECT-TYPE
    		SYNTAX  OBJECT IDENTIFIER
    		ACCESS  read-only
    		STATUS  mandatory
    		DESCRIPTION
           		"This identifies the ATM traffic enforcement type is 7.
                       	For type 7 traffic enforcement, parameter 1
                       	specifies CLP=0+1 peak traffic and parameter
                       	2 specifies best effort traffic
                       	(e.g., a value 1 may be used to indicate
                       	best effort traffic).  Parameters 3, 4 and 5 are not used."
    	::= { aglatmInterfaceTrafficEnforcementTypes  8 }

	aglatmInterfaceConfTable OBJECT-TYPE
    		SYNTAX  SEQUENCE OF AglAtmInterfaceConfEntry
    		ACCESS  not-accessible
    		STATUS  mandatory
    		DESCRIPTION
           		"This table contains ATM local interface configuration
                        parameters and state variables, one
                        entry per ATM interface port."
    	::= { aglatmMIBObjects  2 }

	aglatmInterfaceConfEntry OBJECT-TYPE
    		SYNTAX  AglAtmInterfaceConfEntry
    		ACCESS  not-accessible
    		STATUS  mandatory
    		DESCRIPTION
           		"This list contains ATM interface configuration
                        parameters and state variables."
    		INDEX   { aglatmInterfaceIndex }
    	::= { aglatmInterfaceConfTable  1 }

	AglAtmInterfaceConfEntry ::=
    		SEQUENCE {
        		aglatmInterfaceIndex
            			INTEGER,

        		aglatmInterfaceMaxVpcs
            			INTEGER,

        		aglatmInterfaceMaxVccs
            			INTEGER,

        		aglatmInterfaceConfVpcs
            			INTEGER,

        		aglatmInterfaceConfVccs
            			INTEGER,

        		aglatmInterfaceMaxActiveVpiBits
            			INTEGER,

        		aglatmInterfaceMaxActiveVciBits
            			INTEGER,

        		aglatmInterfaceIlmiVpiVci
            			Interger32,

        		aglatmInterfaceSpecific
            			OBJECT IDENTIFIER
    		}

	aglatmInterfaceIndex OBJECT-TYPE
    		SYNTAX  INTEGER
    		ACCESS  not-accessible
    		STATUS  mandatory
    		DESCRIPTION
           		"The value of this object identifies the ATM port
                        interface for which this entry contains
                        management information."
    	::= { aglatmInterfaceConfEntry  1 }

	aglatmInterfaceMaxVpcs OBJECT-TYPE
    		SYNTAX  INTEGER
    		ACCESS  read-only
    		STATUS  mandatory
    		DESCRIPTION
           		"The maximum number of VPCs supported at
                        this ATM interface."
    	::= { aglatmInterfaceConfEntry  2 }

	aglatmInterfaceMaxVccs OBJECT-TYPE
    		SYNTAX  INTEGER
    		ACCESS  read-only
    		STATUS  mandatory
    		DESCRIPTION
           		"The maximum number of VCCs supported at
                         the ATM interface."
    	::= { aglatmInterfaceConfEntry  3 }

	aglatmInterfaceConfVpcs OBJECT-TYPE
    		SYNTAX  INTEGER
    		ACCESS  read-only
    		STATUS  mandatory
    		DESCRIPTION
           		"The number of VPCs configured for use
                         at this ATM interface."
    	::= { aglatmInterfaceConfEntry  4 }

	aglatmInterfaceConfVccs OBJECT-TYPE
    		SYNTAX  INTEGER
    		ACCESS  read-only
    		STATUS  mandatory
    		DESCRIPTION
           		"The number of VCCs configured for use
                        at the ATM interface."
    	::= { aglatmInterfaceConfEntry  5 }

	aglatmInterfaceMaxActiveVpiBits OBJECT-TYPE
    		SYNTAX  INTEGER
    		ACCESS  read-only
    		STATUS  mandatory
    		DESCRIPTION
           		"The  maximum number of active VPI bits
                        configured for use at the ATM interface."
    	::= { aglatmInterfaceConfEntry  6 }

	aglatmInterfaceMaxActiveVciBits OBJECT-TYPE
    		SYNTAX  INTEGER
    		ACCESS  read-only
    		STATUS  mandatory
    		DESCRIPTION
           		"The maximum number of active VCI bits
                        configured for use at this ATM interface."
    	::= { aglatmInterfaceConfEntry  7 }

	aglatmInterfaceIlmiVpiVci OBJECT-TYPE
    		SYNTAX  INTEGER
    		ACCESS  read-only
    		STATUS  mandatory
    		DESCRIPTION
           		"The decimal value of the three octet VPI/VCI
                        field that identifies the VCC supporting
                        the ILMI at the ATM interface.
                        If the value of this object is greater
                        than 16777215 then the ILMI is not supported
                        at the ATM interface.
                        The default VPI/VCI values for ILMI
                        are VPI=0 and VCI=16."
    	::= { aglatmInterfaceConfEntry  8 }

	aglatmInterfaceSpecific OBJECT-TYPE
    		SYNTAX  OBJECT IDENTIFIER
    		ACCESS  read-only
    		STATUS  mandatory
    		DESCRIPTION
           		"This object points to the additional information
                        specific to ATM interfaces.  For example, if
                        Enterprise specific objects have been defined
                        in addition to this MIB module, then the
                        value of this object refers to that MIB
                        defining these objects.  If the additional
                        information is not present, then the value
                        should be {0 0}."
    	::= { aglatmInterfaceConfEntry  9 }

	aglatmInterfaceDs3PlcpTable OBJECT-TYPE
    		SYNTAX  SEQUENCE OF AglAtmInterfaceDs3PlcpEntry
    		ACCESS  not-accessible
    		STATUS  mandatory
    		DESCRIPTION
           		"This table contains ATM interface DS3 PLCP
                        parameters and state variables, one entry per
                        ATM interface port."
    	::= { aglatmMIBObjects  3 }

	aglatmInterfaceDs3PlcpEntry OBJECT-TYPE
    		SYNTAX  AglAtmInterfaceDs3PlcpEntry
    		ACCESS  not-accessible
    		STATUS  mandatory
    		DESCRIPTION
           		"This list contains DS3 PLCP parameters and
                        state variables at the ATM interface."
    		INDEX   { aglatmInterfaceDs3PlcpIndex }
	::= { aglatmInterfaceDs3PlcpTable  1 }

	AglAtmInterfaceDs3PlcpEntry ::=
    		SEQUENCE {
        		aglatmInterfaceDs3PlcpIndex
            			INTEGER,

        		aglatmInterfaceDs3PlcpSEFSs
            			Counter,

        		aglatmInterfaceDs3PlcpAlarmState
            			INTEGER,

        		aglatmInterfaceDs3PlcpUASs
            			Counter
    		}

	aglatmInterfaceDs3PlcpIndex OBJECT-TYPE
    		SYNTAX  INTEGER
    		ACCESS  not-accessible
    		STATUS  mandatory
    		DESCRIPTION
           		"The value of this object identifies the ATM
                        interface port for which this entry
                        contains management information and is the
                        same as the atmInterfaceIndex."
    	::= { aglatmInterfaceDs3PlcpEntry  1 }

	aglatmInterfaceDs3PlcpSEFSs OBJECT-TYPE
    		SYNTAX  Counter
    		ACCESS  read-only
    		STATUS  mandatory
    		DESCRIPTION
           		"A DS3 Severely Errored Framing Second (SEFS)
                        is a count of one-second intervals
                        containing one or more SEF event."
    	::= { aglatmInterfaceDs3PlcpEntry  2 }

	aglatmInterfaceDs3PlcpAlarmState OBJECT-TYPE
    		SYNTAX  INTEGER {
    				noAlarm(1),
    				receivedFarEndAlarm(2),
    				incomingLOF(3)
			}
    		ACCESS  read-only
    		STATUS  mandatory
    		DESCRIPTION
           		"This variable indicates if there is an
                        alarm present for the DS3 PLCP.  The value
                        receivedFarEndAlarm means that the DS3 PLCP
                        has received an incoming Yellow
                        Signal, the value incomingLOF means that
                        the DS3 PLCP has declared a loss of frame (LOF)
                        failure condition, and the value noAlarm
                        means that there are no alarms present."
    	::= { aglatmInterfaceDs3PlcpEntry  3 }

	aglatmInterfaceDs3PlcpUASs OBJECT-TYPE
    		SYNTAX  Counter
    		ACCESS  read-only
    		STATUS  mandatory
    		DESCRIPTION
           		"The counter associated with the number of
                        Unavailable Seconds encountered by the PLCP."
    	::= { aglatmInterfaceDs3PlcpEntry  4 }

	aglatmInterfaceSonetTCTable OBJECT-TYPE
    		SYNTAX  SEQUENCE OF AglAtmInterfaceSonetTCEntry
    		ACCESS  not-accessible
    		STATUS  mandatory
    		DESCRIPTION
           		"This table contains ATM interface SONET TC
                        Sublayer parameters and state variables,
                        one entry per ATM interface port."
    	::= { aglatmMIBObjects  4 }

	aglatmInterfaceSonetTCEntry OBJECT-TYPE
    		SYNTAX  AglAtmInterfaceSonetTCEntry
    		ACCESS  not-accessible
    		STATUS  mandatory
    		DESCRIPTION
           		"This list contains SONET TC Sublayer parameters
                        and state variables at the ATM interface."
    		INDEX   { aglatmInterfaceSonetTCIndex }
    	::= { aglatmInterfaceSonetTCTable  1 }

	AglAtmInterfaceSonetTCEntry ::=
    		SEQUENCE {
        		aglatmInterfaceSonetTCIndex
            			INTEGER,

        		aglatmInterfaceSonetTCOCDEvents
            			Counter,

        		aglatmInterfaceSonetTCAlarmState
            			INTEGER
    	}

	aglatmInterfaceSonetTCIndex OBJECT-TYPE
    		SYNTAX  INTEGER
    		ACCESS  not-accessible
    		STATUS  mandatory
    		DESCRIPTION
           		"The value of this object identifies the ATM
                        interface port for which this entry
                        contains management information and is
                        the same as the atmInterfaceIndex."
    	::= { aglatmInterfaceSonetTCEntry  1 }

	aglatmInterfaceSonetTCOCDEvents OBJECT-TYPE
    		SYNTAX  Counter
    		ACCESS  read-only
    		STATUS  mandatory
    		DESCRIPTION
           		"The number of times the Out of Cell
                        Delineation (OCD) events occur.  If seven
                        consecutive ATM cells have Header Error
                        Control (HEC) violations, an OCD event occurs.
                        A high number of OCD events may indicate a problem
                        with the SONET TC Sublayer."
    	::= { aglatmInterfaceSonetTCEntry  2 }

	aglatmInterfaceSonetTCAlarmState OBJECT-TYPE
    		SYNTAX  INTEGER {
    				noAlarm(1),
    				lcdFailure(2)
			}
    		ACCESS  read-only
    		STATUS  mandatory
    		DESCRIPTION
           		"This variable indicates if there is an
                        alarm present for the SONET TC Sublayer.  The value
                        lcdFailure indicates that a Loss of
                        Cell Delineation (LCD) failure state has been
                        declared for the SONET TC Sublayer."
    	::= { aglatmInterfaceSonetTCEntry  3 }



	-- aglsonetMIB OBJECT IDENTIFIER ::= { aglSNP 2 }

	aglsonetMIB OBJECT IDENTIFIER ::= { gigaswitch 6 }

	aglsonetObjects OBJECT IDENTIFIER ::= { aglsonetMIB  1 }

	aglsonetObjectsPath OBJECT IDENTIFIER ::= { aglsonetMIB  2 }

	aglsonetMedium OBJECT IDENTIFIER ::= { aglsonetObjects  1 }

	aglsonetSection OBJECT IDENTIFIER ::= { aglsonetObjects  2 }

	aglsonetLine OBJECT IDENTIFIER ::= { aglsonetObjects  3 }

	aglsonetPath OBJECT IDENTIFIER ::= { aglsonetObjectsPath  1 }


	aglsonetMediumTable OBJECT-TYPE
    		SYNTAX  SEQUENCE OF AglSonetMediumEntry
    		ACCESS  not-accessible
    		STATUS  mandatory
    		DESCRIPTION
           		"The SONET/SDH Medium table."
    	::= { aglsonetMedium  1 }

	aglsonetMediumEntry OBJECT-TYPE
    		SYNTAX  AglSonetMediumEntry
    		ACCESS  not-accessible
    		STATUS  mandatory
    		DESCRIPTION
           		"An entry in the SONET/SDH Medium table."
    		INDEX   { aglsonetMediumIfIndex }
    	::= { aglsonetMediumTable  1 }

	AglSonetMediumEntry ::=
    		SEQUENCE {
        		aglsonetMediumIfIndex
            			INTEGER,

        		aglsonetMediumType
            			INTEGER,

        		aglsonetMediumTimeElapsed
            			INTEGER (-2147483648..2147483647),

        		aglsonetMediumValidIntervals
            			INTEGER (-2147483648..2147483647),

        		aglsonetMediumLineCoding
            			INTEGER,

        		aglsonetMediumLineType
            			INTEGER,

        		aglsonetMediumCircuitIdentifier
            			DisplayString
    		}

	aglsonetMediumIfIndex OBJECT-TYPE
    		SYNTAX  INTEGER
    		ACCESS  not-accessible
    		STATUS  mandatory
    		DESCRIPTION
           		"An index value that uniquely identifies a SONET/SDH
                  	Medium/Section/Line Interface."
    	::= { aglsonetMediumEntry  1 }

	aglsonetMediumType OBJECT-TYPE
    		SYNTAX  INTEGER {
    				sonet(1),
    				sdh(2)
			}
    		ACCESS  read-only
    		STATUS  mandatory
    		DESCRIPTION
           		"This variable identifies whether a SONET
                 	or a SDH signal is used across this interface."
    	::= { aglsonetMediumEntry  2 }

	aglsonetMediumTimeElapsed OBJECT-TYPE
    		SYNTAX  INTEGER
    		ACCESS  read-only
    		STATUS  mandatory
    		DESCRIPTION
           		"The number of seconds, including partial
                 	seconds, that have elapsed since the beginning of
                 	the current error-measurement period."
    	::= { aglsonetMediumEntry  3 }

	aglsonetMediumValidIntervals OBJECT-TYPE
    		SYNTAX  INTEGER
    		ACCESS  read-only
    		STATUS  mandatory
    		DESCRIPTION
           		"The number of previous intervals for which valid
                 	data has been stored.  A SONET device must support
                 	at least n intervals.
                 	The minimum value of n is 4.
                 	The default of n is 32.
                 	The maximum value of n is 96.
                 	The value of this object will be n unless
                 	the device was brought online within the last
                 	(nx15) minutes, in which case the value will be the
                 	number of complete 15 minute intervals the device has
                 	been online."
    	::= { aglsonetMediumEntry  4 }

	aglsonetMediumLineCoding OBJECT-TYPE
    		SYNTAX  INTEGER {
    				sonetMediumOther(1),
    				sonetMediumB3ZS(2),
    				sonetMediumCMI(3),
    				sonetMediumNRZ(4),
    				sonetMediumRZ(5)
			}
    		ACCESS  read-only
    		STATUS  mandatory
    		DESCRIPTION
           		"This variable describes the line coding for
                 	this interface. The B3ZS and CMI are used for
                 	electrical SONET/SDH signals (STS-1 and STS-3).
                 	The Non-Return to Zero (NRZ) and the Return
                 	to Zero are used for optical SONET/SDH signals."
    	::= { aglsonetMediumEntry  5 }

	aglsonetMediumLineType OBJECT-TYPE
    		SYNTAX  INTEGER {
    				sonetOther(1),
    				sonetShortSingleMode(2),
    				sonetLongSingleMode(3),
    				sonetMultiMode(4),
    				sonetCoax(5),
    				sonetUTP(6)
			}
    		ACCESS  read-only
    		STATUS  mandatory
    		DESCRIPTION
           		"This variable describes the line type for
                 	this interface. The line types are
                 	Short and Long Range
                 	Single Mode fiber or Multi-Mode fiber interfaces,
                 	and coax and UTP for electrical interfaces.  The
                 	value sonetOther should be used when the Line Type is
                 	not one of the listed values."
    	::= { aglsonetMediumEntry  6 }

	aglsonetMediumCircuitIdentifier OBJECT-TYPE
    		SYNTAX  DisplayString
    		ACCESS  read-only
    		STATUS  mandatory
    		DESCRIPTION
           		"This variable contains the transmission
                 	vendor's circuit identifier, for the
                 	purpose of facilitating troubleshooting."
    	::= { aglsonetMediumEntry  7 }

	aglsonetSectionCurrentTable OBJECT-TYPE
    		SYNTAX  SEQUENCE OF AglSonetSectionCurrentEntry
    		ACCESS  not-accessible
    		STATUS  mandatory
    		DESCRIPTION
           		"The SONET/SDH Section Current table."
    	::= { aglsonetSection  1 }

	aglsonetSectionCurrentEntry OBJECT-TYPE
    		SYNTAX  AglSonetSectionCurrentEntry
    		ACCESS  not-accessible
    		STATUS  mandatory
    		DESCRIPTION
           		"An entry in the SONET/SDH Section Current table."
    		INDEX   { aglsonetSectionCurrentIfIndex }
    	::= { aglsonetSectionCurrentTable  1 }

	AglSonetSectionCurrentEntry ::=
    		SEQUENCE {
        		aglsonetSectionCurrentIfIndex
            			INTEGER,

        		aglsonetSectionCurrentStatus
            			INTEGER (-2147483648..2147483647),

        		aglsonetSectionCurrentESs
            			Gauge,

        		aglsonetSectionCurrentSESs
            			Gauge,

        		aglsonetSectionCurrentSEFSs
            			Gauge,

        		aglsonetSectionCurrentCVs
            			Gauge
    	}

	aglsonetSectionCurrentIfIndex OBJECT-TYPE
    		SYNTAX  INTEGER
    		ACCESS  not-accessible
    		STATUS  mandatory
    		DESCRIPTION
           		"The index value which uniquely identifies the
                 	SONET/SDH Medium/Section/Line Interface."
    	::= { aglsonetSectionCurrentEntry  1 }

	aglsonetSectionCurrentStatus OBJECT-TYPE
    		SYNTAX  INTEGER
    		ACCESS  read-only
    		STATUS  mandatory
    		DESCRIPTION
           		"This variable indicates the
                 	status of the interface.
                 	The sonetSectionStatus
                 	is a bit map represented
                 	as a sum, therefore,
                 	it can represent multiple defects
                 	simultaneously.
                 	The sonetSectionNoDefect should be
                 	set if and only if
                 	no other flag is set.

                 	The various bit positions are:
                       	1   sonetSectionNoDefect
                       	2   sonetSectionLOS
                       	4   sonetSectionLOF"
    	::= { aglsonetSectionCurrentEntry  2 }

	aglsonetSectionCurrentESs OBJECT-TYPE
    		SYNTAX  Gauge
    		ACCESS  read-only
    		STATUS  mandatory
    		DESCRIPTION
           		"The counter associated with the number of Errored
                 	Seconds encountered by a SONET/SDH
                 	Section in the current 15 minute interval."
    	::= { aglsonetSectionCurrentEntry  3 }

	aglsonetSectionCurrentSESs OBJECT-TYPE
    		SYNTAX  Gauge
    		ACCESS  read-only
    		STATUS  mandatory
    		DESCRIPTION
           		"The counter associated with the number of
                 	Severely Errored Seconds
                 	encountered by a SONET/SDH Section in the current 15
                 	minute interval."
    	::= { aglsonetSectionCurrentEntry  4 }

	aglsonetSectionCurrentSEFSs OBJECT-TYPE
    		SYNTAX  Gauge
    		ACCESS  read-only
    		STATUS  mandatory
    		DESCRIPTION
           		"The counter associated with the number of
                 	Severely Errored Framing Seconds
                 	encountered by a SONET/SDH Section in the current
                 	15 minute interval."
    	::= { aglsonetSectionCurrentEntry  5 }

	aglsonetSectionCurrentCVs OBJECT-TYPE
    		SYNTAX  Gauge
    		ACCESS  read-only
    		STATUS  mandatory
    		DESCRIPTION
           		"The counter associated with the number of Coding
                 	Violations encountered by a
                 	SONET/SDH Section in the current 15 minute interval."
    	::= { aglsonetSectionCurrentEntry  6 }

	aglsonetLineCurrentTable OBJECT-TYPE
    		SYNTAX  SEQUENCE OF AglSonetLineCurrentEntry
    		ACCESS  not-accessible
    		STATUS  mandatory
    		DESCRIPTION
           		"The SONET/SDH Line Current table."
    	::= { aglsonetLine  1 }

	aglsonetLineCurrentEntry OBJECT-TYPE
    		SYNTAX  AglSonetLineCurrentEntry
    		ACCESS  not-accessible
    		STATUS  mandatory
    		DESCRIPTION
           		"An entry in the SONET/SDH Line Current table."
    		INDEX   { aglsonetLineCurrentIfIndex }
    	::= { aglsonetLineCurrentTable  1 }

	AglSonetLineCurrentEntry ::=
    		SEQUENCE {
        		aglsonetLineCurrentIfIndex
            			INTEGER,

        		aglsonetLineCurrentStatus
            			INTEGER (-2147483648..2147483647),

        		aglsonetLineCurrentESs
            			Gauge,

        		aglsonetLineCurrentSESs
            			Gauge,

        		aglsonetLineCurrentCVs
            			Gauge,

        		aglsonetLineCurrentUASs
            			Gauge
    		}

	aglsonetLineCurrentIfIndex OBJECT-TYPE
    		SYNTAX  INTEGER
    		ACCESS  not-accessible
    		STATUS  mandatory
    		DESCRIPTION
           		"The index value which uniquely identifies the
                	SONET/SDH Medium/Line Interface."
    	::= { aglsonetLineCurrentEntry  1 }

	aglsonetLineCurrentStatus OBJECT-TYPE
    		SYNTAX  INTEGER
    		ACCESS  read-only
    		STATUS  mandatory
    		DESCRIPTION
           		"This variable indicates the
                 	status of the interface.
                 	The sonetLineStatus
                 	is a bit map represented
                 	as a sum, therefore,
                 	it can represent multiple defects
                 	simultaneously.
                 	The sonetLineNoDefect should be
                 	set if and only if
                 	no other flag is set.

                 	The various bit positions are:
                  	1   sonetLineNoDefect
                  	2   sonetLineAIS
                  	4   sonetLineRDI"
    	::= { aglsonetLineCurrentEntry  2 }

	aglsonetLineCurrentESs OBJECT-TYPE
    		SYNTAX  Gauge
    		ACCESS  read-only
    		STATUS  mandatory
    		DESCRIPTION
           		"The counter associated with the number of Errored
               		Seconds encountered by a SONET/SDH
               		Line in the current 15 minute interval."
    	::= { aglsonetLineCurrentEntry  3 }

	aglsonetLineCurrentSESs OBJECT-TYPE
    		SYNTAX  Gauge
    		ACCESS  read-only
    		STATUS  mandatory
    		DESCRIPTION
           		"The counter associated with the number of
               		Severely Errored Seconds
               		encountered by a SONET/SDH Line in the current 15
               		minute
               		interval."
    	::= { aglsonetLineCurrentEntry  4 }

	aglsonetLineCurrentCVs OBJECT-TYPE
    		SYNTAX  Gauge
    		ACCESS  read-only
    		STATUS  mandatory
    		DESCRIPTION
           		"The counter associated with the number of Coding
               		Violations encountered by a
               		SONET/SDH Line in the current 15 minute interval."
    	::= { aglsonetLineCurrentEntry  5 }

	aglsonetLineCurrentUASs OBJECT-TYPE
    		SYNTAX  Gauge
    		ACCESS  read-only
    		STATUS  mandatory
    		DESCRIPTION
           		"The counter associated with the number of
               		Unavailable Seconds
               		encountered by a SONET/SDH Line in the current 15
               		minute
               		interval."
    	::= { aglsonetLineCurrentEntry  6 }

	aglsonetPathCurrentTable OBJECT-TYPE
    		SYNTAX  SEQUENCE OF AglSonetPathCurrentEntry
    		ACCESS  not-accessible
    		STATUS  mandatory
    		DESCRIPTION
           		"The SONET/SDH Path Current table."
    	::= { aglsonetPath  1 }

	aglsonetPathCurrentEntry OBJECT-TYPE
    		SYNTAX  AglSonetPathCurrentEntry
    		ACCESS  not-accessible
    		STATUS  mandatory
    		DESCRIPTION
           		"An entry in the SONET/SDH Path Current table."
    		INDEX   { aglsonetPathCurrentIfIndex }
    	::= { aglsonetPathCurrentTable  1 }

	AglSonetPathCurrentEntry ::=
    		SEQUENCE {
        		aglsonetPathCurrentIfIndex
            			INTEGER,

        		aglsonetPathCurrentWidth
            			INTEGER,

        		aglsonetPathCurrentStatus
            			INTEGER (-2147483648..2147483647),

        		aglsonetPathCurrentESs
            			Gauge,

        		aglsonetPathCurrentSESs
            			Gauge,

        		aglsonetPathCurrentCVs
            			Gauge,

        		aglsonetPathCurrentUASs
            			Gauge
    		}

	aglsonetPathCurrentIfIndex OBJECT-TYPE
    		SYNTAX  INTEGER
    		ACCESS  not-accessible
    		STATUS  mandatory
    		DESCRIPTION
           		"An index value that uniquely identifies a SONET/SDH
               		Path Interface."
    	::= { aglsonetPathCurrentEntry  1 }

	aglsonetPathCurrentWidth OBJECT-TYPE
    		SYNTAX  INTEGER {
    				sts1(1),
    				sts3cSTM1(2),
    				sts12cSTM4(3),
    				sts24c(4),
    				sts48cSTM16(5)
			}
    		ACCESS  read-write
    		STATUS  mandatory
    		DESCRIPTION
           		"A value that indicates the type of the SONET/SDH
               		Path.  For SONET, the assigned types are
               		the STS-Nc SPEs, where N = 1, 3, 12, 24, and 48.
               		STS-1 is equal to 51.84 Mbps.  For SDH, the assigned
               		types are the STM-Nc VCs, where N = 1, 4, and 16."
    	::= { aglsonetPathCurrentEntry  2 }

	aglsonetPathCurrentStatus OBJECT-TYPE
    		SYNTAX  INTEGER
    		ACCESS  read-only
    		STATUS  mandatory
    		DESCRIPTION
           		"This variable indicates the
                	status of the interface.
                	The sonetPathStatus
                	is a bit map represented
                	as a sum, therefore,
                	it can represent multiple defects
                	simultaneously.
                	The sonetPathNoDefect should be
                	set if and only if
                	no other flag is set.

                	The various bit positions are:
                   	1   sonetPathNoDefect
                   	2   sonetPathSTSLOP
                   	4   sonetPathSTSAIS
                   	8   sonetPathSTSRDI
                  	16   sonetPathUnequipped
                  	32   sonetPathSignalLabelMismatch"
    	::= { aglsonetPathCurrentEntry  3 }

	aglsonetPathCurrentESs OBJECT-TYPE
    		SYNTAX  Gauge
    		ACCESS  read-only
    		STATUS  mandatory
    		DESCRIPTION
           		"The counter associated with the number of Errored
               		Seconds encountered by a SONET/SDH
               		Path in the current 15 minute interval."
    	::= { aglsonetPathCurrentEntry  4 }

	aglsonetPathCurrentSESs OBJECT-TYPE
    		SYNTAX  Gauge
    		ACCESS  read-only
    		STATUS  mandatory
    		DESCRIPTION
           		"The counter associated with the number of
               		Severely Errored Seconds
               		encountered by a SONET/SDH Path in the current 15
               		minute interval."
    	::= { aglsonetPathCurrentEntry  5 }

	aglsonetPathCurrentCVs OBJECT-TYPE
    		SYNTAX  Gauge
    		ACCESS  read-only
    		STATUS  mandatory
    		DESCRIPTION
           		"The counter associated with the number of Coding
               		Violations encountered by a
               		SONET/SDH Path in the current 15 minute interval."
    	::= { aglsonetPathCurrentEntry  6 }

	aglsonetPathCurrentUASs OBJECT-TYPE
    		SYNTAX  Gauge
    		ACCESS  read-only
    		STATUS  mandatory
    		DESCRIPTION
           		"The counter associated with the number of
               		Unavailable Seconds
               		encountered by a Path in the current
               		15 minute, interval."
    	::= { aglsonetPathCurrentEntry  7 }





	END
