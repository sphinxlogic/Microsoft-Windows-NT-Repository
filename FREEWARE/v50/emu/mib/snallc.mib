-- MIB created 1/17/96 13:42:04, by
--   SMIC (the next generation) version 1.6.29, November 22, 1994.

CISCO-SNA-LLC-MIB DEFINITIONS ::= BEGIN

-- From file: "CISCO-SNA-LLC-MIB.my"

IMPORTS
    Counter32, Integer32, TimeTicks, Gauge32
            FROM SNMPv2-SMI-v1
    OBJECT-TYPE
            FROM RFC-1212
    TRAP-TYPE
            FROM RFC-1215
    DisplayString, RowStatus, TimeStamp, MacAddress
            FROM SNMPv2-TC-v1
    ifIndex
            FROM RFC1213-MIB
    ciscoExperiment
            FROM CISCO-SMI;

ciscoSnaLlcMIB OBJECT IDENTIFIER ::= { ciscoExperiment 8 }
-- MODULE-IDENTITY
--  LastUpdated
--    9505100000Z
--  OrgName
--    cisco IBM engineering Working Group
--  ContactInfo
--     Cisco Systems
--     Customer Service
--    
--    Postal: 170 W Tasman Drive
--     San Jose, CA  95134
--     USA
--    
--       Tel: +1 800 553-NETS
--    
--    E-mail: cs-snmp@cisco.com
--  Descr
--    This is the MIB module for objects used to
--    manage LLC devices.
--  RevDate
--    9505100000Z
--  RevDescr
--    Initial version of this MIB module.

ciscoSnaLlcMIBObjects OBJECT IDENTIFIER ::= { ciscoSnaLlcMIB 1 }
llcPortGroup    OBJECT IDENTIFIER ::= { ciscoSnaLlcMIBObjects 1 }
llcSapGroup     OBJECT IDENTIFIER ::= { ciscoSnaLlcMIBObjects 2 }
llcCcGroup      OBJECT IDENTIFIER ::= { ciscoSnaLlcMIBObjects 3 }
snaLlcMIBNotificationPrefix OBJECT IDENTIFIER ::= { ciscoSnaLlcMIB 2 }
snaLlcMIBNotifications OBJECT IDENTIFIER ::= { snaLlcMIBNotificationPrefix 0 }
snaLlcMIBConformance OBJECT IDENTIFIER ::= { ciscoSnaLlcMIB 3 }
snaLlcMIBCompliances OBJECT IDENTIFIER ::= { snaLlcMIBConformance 1 }
snaLlcMIBGroups OBJECT IDENTIFIER ::= { snaLlcMIBConformance 2 }

llcPortAdminTable OBJECT-TYPE
    SYNTAX SEQUENCE OF LlcPortAdminEntry
    ACCESS not-accessible
    STATUS mandatory
    DESCRIPTION
        "This table contains objects that can be
         changed to manage an LLC port. Changing one
         of these parameters may take effect in the
         operating port immediately or may wait until
         the interface is restarted depending on the
         details of the implementation."
    ::= { llcPortGroup 1 }

llcPortAdminEntry OBJECT-TYPE
    SYNTAX LlcPortAdminEntry
    ACCESS not-accessible
    STATUS mandatory
    DESCRIPTION
        "A list of configured values for an LLC port."
    INDEX { ifIndex, llcPortVirtualIndex }
    ::= { llcPortAdminTable 1 }

LlcPortAdminEntry ::= SEQUENCE {
    llcPortVirtualIndex Integer32,
    llcPortAdminName DisplayString,
    llcPortAdminMaxSaps Gauge32,
    llcPortAdminMaxCcs Gauge32,
    llcPortAdminMaxPDUOctets Integer32,
    llcPortAdminMaxUnackedIPDUsSend INTEGER,
    llcPortAdminMaxUnackedIPDUsRcv INTEGER,
    llcPortAdminMaxRetransmits Integer32,
    llcPortAdminAckTimer TimeTicks,
    llcPortAdminPbitTimer TimeTicks,
    llcPortAdminRejTimer TimeTicks,
    llcPortAdminBusyTimer TimeTicks,
    llcPortAdminInactTimer TimeTicks,
    llcPortAdminDelayAckCount Integer32,
    llcPortAdminDelayAckTimer TimeTicks,
    llcPortAdminNw Integer32
    }

llcPortVirtualIndex OBJECT-TYPE
    SYNTAX Integer32(0..65535)
    ACCESS not-accessible
    STATUS mandatory
    DESCRIPTION
        "This value represents a virtual LLC port.
         It is assigned by the agent. 
         
         This value is set to 0 by the agent for 
         interfaces identified by the ifIndex value
         that do not support virtual interfaces."
    ::= { llcPortAdminEntry 1 }

llcPortAdminName OBJECT-TYPE
    SYNTAX DisplayString(SIZE(1..8))
--    Rsyntax OCTET STRING(SIZE(1..8))
    ACCESS read-write
    STATUS mandatory
    DESCRIPTION
        "An octet string that defines the virtual port
        to which this interface is assigned.  Its value
        shall be unique within the administered
        system.  It must contain only ASCII printable
        characters.  A write operation shall not take 
        effect until the port is cycled inactive."
    ::= { llcPortAdminEntry 2 }

llcPortAdminMaxSaps OBJECT-TYPE
    SYNTAX Gauge32
    ACCESS read-write
    STATUS mandatory
    DESCRIPTION
        "This parameter specifies the maximum number of
        SAPs that can be defined for this port."
    ::= { llcPortAdminEntry 3 }

llcPortAdminMaxCcs OBJECT-TYPE
    SYNTAX Gauge32
    ACCESS read-write
    STATUS mandatory
    DESCRIPTION
        "This parameter specifies the maximum number of
        connection components that can be
        administratively defined for this port."
    ::= { llcPortAdminEntry 4 }

llcPortAdminMaxPDUOctets OBJECT-TYPE
    SYNTAX Integer32
--  Units
--    octets
    ACCESS read-write
    STATUS mandatory
    DESCRIPTION
        "This object denotes the default maximum I PDU
        size, in octets, that LLCs on this port may
        send to their remote LLC partners. This count
        is referred to as 'N1' in the IEEE 802.2
        specification [5].
        
        This port default value may be overridden by a
        non-zero SAP default value in the
        llcSapAdminMaxIPDUOctetsSend  object or by a
        non-zero value in the
        llcCcAdminMaxIPDUOctetsSend object.
        
        At connection setup, the remote LLC may send,
        using an XID frame, the maximum I PDU size
        which it is prepared to receive. If so, an
        implementation may choose to override the
        administered maximum PDU size with the
        dynamically learned value and should reflect
        this in the llcCcOperMaxIPDUOctetsSend object
        for the connection component.
        
        The I PDU size includes all octets in a frame,
        excluding framing characters, the MAC header
        and link header."
    REFERENCE
        "ISO 8802-2 : 1989, ANSI/IEEE 802.2 - 1989
         Section 7.8.3
         Maximum Number of Octets in an I PDU, N1."
    ::= { llcPortAdminEntry 5 }

llcPortAdminMaxUnackedIPDUsSend OBJECT-TYPE
    SYNTAX INTEGER(1..127)
    ACCESS read-write
    STATUS mandatory
    DESCRIPTION
        "This object denotes the default maximum
        consecutive unacknowledged I PDU frames that
        LLCs on this port may send to their remote LLC
        partners. This count is referred to as 'k' in
        the IEEE 802.2 specification [5].
        
        This port default value may be overridden by a
        non-zero SAP default value in the
        llcSapAdminMaxUnackedIPDUsSend  object or by a
        non-zero value in the
        llcCcAdminMaxUnackedIPDUsSend object.
        
        At connection setup, the remote LLC may send,
        using an XID frame, the maximum number of
        unacknowledged I PDUs which it is prepared to
        receive. If so, an implementation may choose to
        override the administered maximum number of
        unacknowledged PDUs with the dynamically learned
        value and should reflect this in the
        llcCcOperMaxUnackedIPDUsSend object for the
        connection component."
    REFERENCE
        "ISO 8802-2 : 1989, ANSI/IEEE 802.2 - 1989
         Section 7.8.4
         Maximum Number of Outstanding I PDUs, k."
    DEFVAL { 2 }
    ::= { llcPortAdminEntry 6 }

llcPortAdminMaxUnackedIPDUsRcv OBJECT-TYPE
    SYNTAX INTEGER(1..127)
    ACCESS read-write
    STATUS mandatory
    DESCRIPTION
        "This object denotes the default maximum number
        of unacknowledged I PDUs that LLCs on this port
        can expect to receive from their remote LLC
        partners. This count is referred to as 'k' in
        the IEEE 802.2 specification [5].
        
        This port default value may be overridden by a
        non-zero SAP default value in the
        llcSapAdminMaxUnackedIPDUsRcv object or by a
        non-zero value in the
        llcCcAdminMaxUnackedIPDUsRcvd object.
        
        At connection setup, an implementation may
        choose to send this value to the remote LLC,
        using an XID frame."
    REFERENCE
        "ISO 8802-2 : 1989, ANSI/IEEE 802.2 - 1989
         Section 7.8.4
         Maximum Number of Outstanding I PDUs, k."
    DEFVAL { 2 }
    ::= { llcPortAdminEntry 7 }

llcPortAdminMaxRetransmits OBJECT-TYPE
    SYNTAX Integer32
    ACCESS read-write
    STATUS mandatory
    DESCRIPTION
        "This object denotes the default value for the
        maximum number of times which LLCs on this port
        shall retry a PDU following the expiration of
        the acknowledgement timer, the P-bit timer or
        the reject timer. When these retries are
        exhausted, the link shall be declared inactive.
        This count is referred to as 'N2' in the IEEE
        802.2 specification [5].
        
        This port default value may be overridden by a
        non-zero SAP default value in the
        llcSapAdminMaxretransmits object or by a
        non-zero value in the llcCcAdminMaxRetransmits
        object."
    REFERENCE
        "ISO 8802-2 : 1989, ANSI/IEEE 802.2 - 1989
         Section 7.8.2
         Maximum Number of Transmissions, N2."
    DEFVAL { 2 }
    ::= { llcPortAdminEntry 8 }

llcPortAdminAckTimer OBJECT-TYPE
    SYNTAX TimeTicks
    ACCESS read-write
    STATUS mandatory
    DESCRIPTION
        "This object denotes the default value for the
        time interval during which the LLCs on this port
        shall expect to receive either:
        
        1) an acknowledgement to one or more outstanding
        I PDUs.  or 2) a response PDU to an unnumbered
        command PDU.
        
        The expiration of this timer shall cause the
        unacknowledged frames to be retransmitted
        (up to N2 times).
        
        For Implementations that only use a single
        'T1' Value (ref. IBM Token-Ring Network
        technical reference Chapter 11).  This object
        will be used to control/read the value.
        
        This port default value may be overridden by a
        non-zero value in the llcSapAdminAckTimer object
        or by a non-zero value in the llcCcAdminAckTimer
        object."
    REFERENCE
        "ISO 8802-2 : 1989, ANSI/IEEE 802.2 - 1989
         Section 7.8.1.1
         Acknowledgment Timer"
    DEFVAL { 300 }
    ::= { llcPortAdminEntry 9 }

llcPortAdminPbitTimer OBJECT-TYPE
    SYNTAX TimeTicks
    ACCESS read-write
    STATUS mandatory
    DESCRIPTION
        "This object denotes the default value for the
        time interval during which the LLCs on this
        port shall expect to receive a PDU with the F
        bit set to '1' in response to a Type 2 command
        with the P bit set to '1'.
        
        The expiration of this timer shall cause the
        command with the poll bit to be retransmitted
        (up to N2 times).
        
        This port default value may be overridden by a
        non-zero SAP default value in the
        llcSapAdminPbitTimer object or by a non-zero
        value in the llcCcAdminPbitTimer object."
    REFERENCE
        "ISO 8802-2 : 1989, ANSI/IEEE 802.2 - 1989
         Section 7.8.1.2
         P-Bit Timer"
    DEFVAL { 300 }
    ::= { llcPortAdminEntry 10 }

llcPortAdminRejTimer OBJECT-TYPE
    SYNTAX TimeTicks
    ACCESS read-write
    STATUS mandatory
    DESCRIPTION
        "This object denotes the default value for the
        time interval during which the LLCs on this
        port shall expect to receive a reply to a REJ
        PDU.
        
        The expiration of this timer shall cause the
        REJ PDU to be retransmitted (up to N2 times).
        
        This port default value may be overridden by a
        non-zero SAP default value in the
        llcSapAdminRejTimer object or by a non-zero
        value in the llcCcAdminRejTimer object."
    REFERENCE
        "ISO 8802-2 : 1989, ANSI/IEEE 802.2 - 1989
         Section 7.8.1.3
         Reject Timer"
    DEFVAL { 300 }
    ::= { llcPortAdminEntry 11 }

llcPortAdminBusyTimer OBJECT-TYPE
    SYNTAX TimeTicks
    ACCESS read-write
    STATUS mandatory
    DESCRIPTION
        "This object denotes the default value for the
        time interval during which the LLCs on this
        port shall expect to receive an indication that
        a busy condition at the remote LLC has
        cleared.
        
        The expiration of this timer shall cause the
        link to be declared inactive.
        
        This port default value may be overridden by a
        non-zero SAP default value in the
        llcSapAdminBusyTimer object or by a non-zero
        value in the llcCcAdminBusyTimer object."
    REFERENCE
        "ISO 8802-2 : 1989, ANSI/IEEE 802.2 - 1989
         Section 7.8.1.4
         Busy-State Timer"
    DEFVAL { 30000 }
    ::= { llcPortAdminEntry 12 }

llcPortAdminInactTimer OBJECT-TYPE
    SYNTAX TimeTicks
    ACCESS read-write
    STATUS mandatory
    DESCRIPTION
        "This object denotes the default value for the
        time interval during which the LLCs on this
        port shall expect to receive any PDU from the
        remote LLC.  This function is not described in
        the IEEE 802.2 specification [5].  It is listed
        in the IBM Token-Ring Network Architecture [6]
        Reference as the Ti parameter and is widely
        implemented.
        
        The expiration of this timer shall cause the
        local LLC to send a PDU to the remote LLC with
        the P bit set to '1'.
        
        The value for llcPortAdminInactTimer must be
        much greater than the value for
        llcPortAdminDelayAckTimer.
        
        This port default value may be overridden by a
        non-zero SAP default value in the
        llcSapAdminInactTimer object or by a non-zero
        value in the llcCcAdminInactTimer object.
        
        Any value for this object less than or equal to
        the acknowledgement timer shall mean that the
        timer is not used."
    REFERENCE
        "IBM Token-Ring Network Architecture Ref. SC30-3374
         Chapter 11: Operation of Link Stations
         Inactivity Timer (Ti)"
    DEFVAL { 3000 }
    ::= { llcPortAdminEntry 13 }

llcPortAdminDelayAckCount OBJECT-TYPE
    SYNTAX Integer32
    ACCESS read-write
    STATUS mandatory
    DESCRIPTION
        "This object denotes the default value for the
        maximum number of consecutive I PDUs which the
        LLCs on this port shall receive during the
        interval defined by llcCcOperDelayTimertime
        without sending an immediate acknowledgement.
        This must be less than or equal to the value of
        llcCcOperMaxUnackIPDURcv. This function is not
        described in the IEEE 802.2 specification [5].
        It is listed in the IBM Token-Ring Network
        Architecture Reference [6] as the N3 parameter
        and is widely implemented.
        
        This port default value may be overridden by a
        non-zero SAP default value in the
        llcSapAdminDelayAckCount object or by a
        non-zero value in the llcCcAdminDelayCount
        object.
        
        A value of one indicates that acknowledgments
        will be sent immediately and that the value of
        llcPortAdminDelayAckTimer shall be ignored."
    REFERENCE
        "IBM Token-Ring Network Architecture Ref. SC30-3374
         Chapter 11: Operation of Link Stations
         Number of I-Format LPDUs Received before
         Sending Acknowledgment (N3)"
    DEFVAL { 1 }
    ::= { llcPortAdminEntry 14 }

llcPortAdminDelayAckTimer OBJECT-TYPE
    SYNTAX TimeTicks
    ACCESS read-write
    STATUS mandatory
    DESCRIPTION
        "This object denotes the default value for the
        time interval during which the LLCs on this
        port shall delay acknowledgment of one or more
        I PDUs (up to the value of
        llcCcOperDelayAckCount). This function is not
        described in the IEEE 802.2 specification [5].
        
        It is listed in the IBM Token-Ring Network
        Architecture Reference [6] as the T2 parameter
        and is widely implemented.
        
        The expiration of this timer shall cause the
        local LLC to acknowledge all unacknowledged I
        PDUs.
        
        This object is associated with the
        llcSapAdminDelayAckCount object and is only
        defined if that object has a value greater than
        one."
    REFERENCE
        "IBM Token-Ring Network Architecture Ref. SC30-3374
         Chapter 11: Operation of Link Stations
         Receiver Acknowledgment Timer (T2)"
    DEFVAL { 100 }
    ::= { llcPortAdminEntry 15 }

llcPortAdminNw OBJECT-TYPE
    SYNTAX Integer32
    ACCESS read-write
    STATUS mandatory
    DESCRIPTION
        "This object denotes the default value for the
        number of IPDUs that must be acknowledged
        before the working window size (Ww) can be
        incremented by 1 when the working window is not
        equal to the maximum transmit window size (TW).
        It controls the gradual incrementing of Ww in
        congestion situations.
        
        This function is not described in the IEEE
        802.2 specification [5].  However, it is listed
        in the IBM Token-Ring Network Architecture
        Reference [6] as the Nw parameter and is widely
        implemented.
        
        This port default value may be overridden by a
        non-zero SAP default value in the llcSapAdminNw
        object."
    REFERENCE
        "IBM Token-Ring Network Architecture Ref.
        SC30-3374 Chapter 11: Operation of Link
        Stations Number of Acknowledgments Needed to
        Increment Ww (Nw)"
    DEFVAL { 4 }
    ::= { llcPortAdminEntry 16 }

llcPortOperTable OBJECT-TYPE
    SYNTAX SEQUENCE OF LlcPortOperEntry
    ACCESS not-accessible
    STATUS mandatory
    DESCRIPTION
        "This table contains current LLC port
        parameters. Many of these objects have
        corresponding objects in the llcPortAdminTable."
    ::= { llcPortGroup 2 }

llcPortOperEntry OBJECT-TYPE
    SYNTAX LlcPortOperEntry
    ACCESS not-accessible
    STATUS mandatory
    DESCRIPTION
        "Currently set parameters for a specific LLC port."
    INDEX { ifIndex, llcPortVirtualIndex }
    ::= { llcPortOperTable 1 }

LlcPortOperEntry ::= SEQUENCE {
    llcPortOperMacAddress MacAddress,
    llcPortOperNumSaps Gauge32,
    llcPortOperHiWaterNumSaps Gauge32,
    llcPortOperSimRim INTEGER,
    llcPortOperLastModifyTime TimeStamp
    }

llcPortOperMacAddress OBJECT-TYPE
    SYNTAX MacAddress
--    Rsyntax OCTET STRING(SIZE(6))
    ACCESS read-only
    STATUS mandatory
    DESCRIPTION
        "This is the MAC Address for this local port."
    ::= { llcPortOperEntry 1 }

llcPortOperNumSaps OBJECT-TYPE
    SYNTAX Gauge32
    ACCESS read-only
    STATUS mandatory
    DESCRIPTION
        "This object defines the number of SAPs on this
        port that are currently enabled.  In other
        words, this object is a count of the number of
        instances of llcSapOperEntry that have a
        llcSapOperStatus value of 'active(2)'."
    ::= { llcPortOperEntry 2 }

llcPortOperHiWaterNumSaps OBJECT-TYPE
    SYNTAX Gauge32
    ACCESS read-only
    STATUS mandatory
    DESCRIPTION
        "This object reflects the highest number of 
        SAPs active on this Port simultaneously. In other words,
        this object is a count of the number of
        instances of llcSapOperEntry on this Port."
    ::= { llcPortOperEntry 3 }

llcPortOperSimRim OBJECT-TYPE
    SYNTAX INTEGER {
        no(1),
        yes(2)
        }
    ACCESS read-only
    STATUS mandatory
    DESCRIPTION
        "This object reflects support for transmission
        and receipt of SIM and RIM control frames for
        this port.
        
        SIM and RIM are not defined in the ANSI/IEEE
        802.2 specification [5] nor in the IBM Token
        Ring Architecture Reference [6].  These
        control frames are used for the remote program
        load of IBM communications processors."
    DEFVAL { no }
    ::= { llcPortOperEntry 4 }

llcPortOperLastModifyTime OBJECT-TYPE
    SYNTAX TimeStamp
--    Rsyntax TimeTicks
    ACCESS read-only
    STATUS mandatory
    DESCRIPTION
        "This object describes the value of sysUpTime
        when this port definition was last modified.
        If the port has not been modified, then this
        value shall be zero."
    ::= { llcPortOperEntry 5 }

llcPortStatsTable OBJECT-TYPE
    SYNTAX SEQUENCE OF LlcPortStatsEntry
    ACCESS not-accessible
    STATUS mandatory
    DESCRIPTION
        "Each entry in this table contains statistics
        for a specific LLC port."
    ::= { llcPortGroup 3 }

llcPortStatsEntry OBJECT-TYPE
    SYNTAX LlcPortStatsEntry
    ACCESS not-accessible
    STATUS mandatory
    DESCRIPTION
        "A list of statistics for an LLC port."
    INDEX { ifIndex, llcPortVirtualIndex }
    ::= { llcPortStatsTable 1 }

LlcPortStatsEntry ::= SEQUENCE {
    llcPortStatsPDUsIn Counter32,
    llcPortStatsPDUsOut Counter32,
    llcPortStatsOctetsIn Counter32,
    llcPortStatsOctetsOut Counter32,
    llcPortStatsTESTCommandsIn Counter32,
    llcPortStatsTESTResponsesOut Counter32,
    llcPortStatsLocalBusies Counter32,
    llcPortStatsUnknownSaps Counter32
    }

llcPortStatsPDUsIn OBJECT-TYPE
    SYNTAX Counter32
    ACCESS read-only
    STATUS mandatory
    DESCRIPTION
        "This object reflects the total number of
        PDUs that have been received on this port.  
        This object is initialized to zero when the 
        port is created."
    ::= { llcPortStatsEntry 1 }

llcPortStatsPDUsOut OBJECT-TYPE
    SYNTAX Counter32
    ACCESS read-only
    STATUS mandatory
    DESCRIPTION
        "This object reflects the total number of
        PDUs that have been transmitted on this port.  
        This object is initialized to zero when the port 
        is created."
    ::= { llcPortStatsEntry 2 }

llcPortStatsOctetsIn OBJECT-TYPE
    SYNTAX Counter32
--  Units
--    octets
    ACCESS read-only
    STATUS mandatory
    DESCRIPTION
        "This object reflects the total octets received
        on this port.  This object is initialized to 
        zero when the port is created."
    ::= { llcPortStatsEntry 3 }

llcPortStatsOctetsOut OBJECT-TYPE
    SYNTAX Counter32
--  Units
--    octets
    ACCESS read-only
    STATUS mandatory
    DESCRIPTION
        "This object reflects the total octets
        transmitted on this port.  This object is 
        initialized to zero when the port is created."
    ::= { llcPortStatsEntry 4 }

llcPortStatsTESTCommandsIn OBJECT-TYPE
    SYNTAX Counter32
    ACCESS read-only
    STATUS mandatory
    DESCRIPTION
        "This object reflects the total number of
        TEST commands received on this port."
    ::= { llcPortStatsEntry 5 }

llcPortStatsTESTResponsesOut OBJECT-TYPE
    SYNTAX Counter32
    ACCESS read-only
    STATUS mandatory
    DESCRIPTION
        "This object reflects the total number of
        TEST responses transmitted on this port
        in response to TEST commands received."
    ::= { llcPortStatsEntry 6 }

llcPortStatsLocalBusies OBJECT-TYPE
    SYNTAX Counter32
    ACCESS read-only
    STATUS mandatory
    DESCRIPTION
        "This object reflects the total number of times
        that the local connection components on this
        port have entered a busy state (RNR).  This
        object is initialized to zero when the port is
        created."
    ::= { llcPortStatsEntry 7 }

llcPortStatsUnknownSaps OBJECT-TYPE
    SYNTAX Counter32
    ACCESS read-only
    STATUS mandatory
    DESCRIPTION
        "This object reflects the total number of times
        that a connection attempt, from a remote LLC
        station, for an unknown SAP was detected on this 
        port."
    ::= { llcPortStatsEntry 8 }

llcSapAdminTable OBJECT-TYPE
    SYNTAX SEQUENCE OF LlcSapAdminEntry
    ACCESS not-accessible
    STATUS mandatory
    DESCRIPTION
        "This table contains objects that can be
        changed to manage a local SAP. Changing one
        of these parameters may take effect in the
        operating CC immediately or may wait until the
        interface is restarted depending on the details
        of the implementation."
    ::= { llcSapGroup 1 }

llcSapAdminEntry OBJECT-TYPE
    SYNTAX LlcSapAdminEntry
    ACCESS not-accessible
    STATUS mandatory
    DESCRIPTION
        "A list of configured values for a local SAP."
    INDEX { ifIndex, llcPortVirtualIndex, llcSapNumber }
    ::= { llcSapAdminTable 1 }

LlcSapAdminEntry ::= SEQUENCE {
    llcSapNumber INTEGER,
    llcSapAdminMaxPDUOctets Integer32,
    llcSapAdminMaxUnackedIPDUsSend INTEGER,
    llcSapAdminMaxUnackedIPDUsRcv INTEGER,
    llcSapAdminMaxRetransmits Integer32,
    llcSapAdminAckTimer TimeTicks,
    llcSapAdminPbitTimer TimeTicks,
    llcSapAdminRejTimer TimeTicks,
    llcSapAdminBusyTimer TimeTicks,
    llcSapAdminInactTimer TimeTicks,
    llcSapAdminDelayAckCount Integer32,
    llcSapAdminDelayAckTimer TimeTicks,
    llcSapAdminNw Integer32
    }

llcSapNumber OBJECT-TYPE
    SYNTAX INTEGER(1..255)
    ACCESS not-accessible
    STATUS mandatory
    DESCRIPTION
        "The address of this local SAP."
    ::= { llcSapAdminEntry 1 }

llcSapAdminMaxPDUOctets OBJECT-TYPE
    SYNTAX Integer32
--  Units
--    octets
    ACCESS read-write
    STATUS mandatory
    DESCRIPTION
        "This object denotes the default maximum I PDU
        size, in octets, that LLCs on this SAP may send
        to their remote connection component partners.
        This count is referred to as 'N1' in the IEEE
        802.2 specification [5].
        
        A zero value for this object indicates that the
        port default, llcPortAdminMaxIPDUOctetsSend,
        shall be used as the SAP default.  This SAP
        default value may be overridden by a non-zero
        value in the llcCcAdminMaxIPDUOctetsSend
        object.
        
        At connection setup, the remote LLC may send,
        using an XID frame, the maximum I PDU size
        which it is prepared to receive. If so, an
        implementation may choose to override the
        administered maximum PDU size with the
        dynamically learned value and should reflect
        this in the llcCcOperMaxIPDUOctetsSend object
        for the connection component.
        
        The I PDU size includes all octets in a frame,
        excluding framing characters, the MAC header
        and link header."
    DEFVAL { 0 }
    ::= { llcSapAdminEntry 2 }

llcSapAdminMaxUnackedIPDUsSend OBJECT-TYPE
    SYNTAX INTEGER(0..127)
    ACCESS read-write
    STATUS mandatory
    DESCRIPTION
        "This object denotes the default maximum
        consecutive unacknowledged I PDU frames that
        LLCs on this SAP may send to their remote LLC
        partners. This count is referred to as 'k' in
        the IEEE 802.2 specification [5].
        
        A zero value for this object indicates that the
        port default, llcPortAdminMaxUnackedIPDUsSend,
        shall be used as the SAP default.  This SAP
        default value may be overridden by a non-zero
        value in the llcCcAdminMaxUnackedIPDUsSend
        object.
        
        At connection setup, the remote LLC may send,
        using an XID frame, the maximum number of
        unacknowledged I PDUs which it is prepared to
        receive. If so, an implementation may choose to
        override the administered maximum number of
        unacknowledged PDUs with the dynamically learned
        value and should reflect this in the
        llcCcOperMaxUnackedIPDUsSend object for the
        connection component."
    DEFVAL { 0 }
    ::= { llcSapAdminEntry 3 }

llcSapAdminMaxUnackedIPDUsRcv OBJECT-TYPE
    SYNTAX INTEGER(0..127)
    ACCESS read-write
    STATUS mandatory
    DESCRIPTION
        "This object denotes the default maximum number
        of unacknowledged I PDUs that LLCs on this SAP
        can expect to receive from their remote LLC
        partners. This count is referred to as 'k' in
        the IEEE 802.2 specification [5].
        
        A zero value for this object indicates that the
        port default, llcPortAdminMaxUnackedIPDUsRcv,
        shall be used as the SAP default.  This SAP
        default value may be overridden by a non-zero
        value in the llcCcAdminMaxUnackedIPDUsRcv
        object.
        
        At connection setup, an implementation may
        choose to send this value to the remote LLC,
        using an XID frame."
    DEFVAL { 0 }
    ::= { llcSapAdminEntry 4 }

llcSapAdminMaxRetransmits OBJECT-TYPE
    SYNTAX Integer32
    ACCESS read-write
    STATUS mandatory
    DESCRIPTION
        "This object denotes the default value for the
        maximum number of times that LLCs on this SAP
        shall retry PDUs following the expiration of
        the acknowledgement timer, the P-bit timer or
        the reject timer. When these retries are
        exhausted, thelink shall be declared inactive.
        This count is referred to as 'N2' in the IEEE
        802.2 specification [5].
        
        A zero value for this object indicates that the
        port default, llcPortAdminMaxRetransmits, shall
        be used as the SAP default.  This SAP default
        value may be overridden by a non-zero value in
        the llcCcAdminMaxRetransmits."
    DEFVAL { 0 }
    ::= { llcSapAdminEntry 5 }

llcSapAdminAckTimer OBJECT-TYPE
    SYNTAX TimeTicks
    ACCESS read-write
    STATUS mandatory
    DESCRIPTION
        "This object denotes the default value for the
        time interval during which the LLCs on this SAP
        shall expect to receive either:
        
        1) an acknowledgement to one or more
        outstanding I PDUs.  or 2) a response PDU to an
        unnumbered command PDU.
        
        The expiration of this timer shall cause the
        frame unacknowledged frames to be retransmitted
        (up to N2 times).
        
        A zero value for this object indicates that the
        port default, llcPortAdminAckTimer, shall be
        used as the SAP default.  This SAP default
        value may be overridden by a non-zero value in
        the llcCcAdminAckTimer."
    DEFVAL { 0 }
    ::= { llcSapAdminEntry 6 }

llcSapAdminPbitTimer OBJECT-TYPE
    SYNTAX TimeTicks
    ACCESS read-write
    STATUS mandatory
    DESCRIPTION
        "This object denotes the default value for the
        time interval during which the LLCs on this
        port shall expect to receive a PDU with the F
        bit set to '1' in response to a Type 2 command
        with the P bit set to '1'.
        
        The expiration of this timer shall cause the
        REJ PDU to be retransmitted (up to N2 times).
        
        A zero value for this object indicates that the
        port default, llcPortAdminPbitTimer, shall be
        used as the SAP default.  This SAP default
        value may be overridden by a non-zero value in
        the llcCcAdminPbitTimer."
    DEFVAL { 0 }
    ::= { llcSapAdminEntry 7 }

llcSapAdminRejTimer OBJECT-TYPE
    SYNTAX TimeTicks
    ACCESS read-write
    STATUS mandatory
    DESCRIPTION
        "This object denotes the default value for the
        time interval during which the LLCs on this SAP
        shall expect to receive a reply to a REJ PDU.
        
        The expiration of this timer shall cause the
        REJ PDU to be retransmitted (up to N2 times).
        
        A zero value for this object indicates that the
        port default, llcPortAdminRejTimer, shall be
        used as the SAP default.  This SAP default
        value may be overridden by a non-zero value in
        the llcCcAdminRejTimer."
    DEFVAL { 0 }
    ::= { llcSapAdminEntry 8 }

llcSapAdminBusyTimer OBJECT-TYPE
    SYNTAX TimeTicks
    ACCESS read-write
    STATUS mandatory
    DESCRIPTION
        "This object denotes the default value for the
        time interval during which the LLCs on this SAP
        shall expect to receive an indication that a
        busy condition at the remote LLC has cleared.
        
        The expiration of this timer shall cause the
        link to be declared inactive.
        
        A zero value for this object indicates that the
        port default, llcPortAdminBusyTimer, shall be
        used as the SAP default.  This SAP default
        value may be overridden by a non-zero value in
        the llcCcAdminBusyTimer."
    DEFVAL { 0 }
    ::= { llcSapAdminEntry 9 }

llcSapAdminInactTimer OBJECT-TYPE
    SYNTAX TimeTicks
    ACCESS read-write
    STATUS mandatory
    DESCRIPTION
        "This object denotes the default value for the
        time interval during which the LLCs on this SAP
        shall expect to receive any PDU from the remote
        LLC.  This function is not described in the
        IEEE 802.2 specification [5] but is widely
        implemented.
        
        The expiration of this timer shall cause the
        local LLC to send a PDU to the remote LLC with
        the P bit set to '1'.
        
        A zero value for this object indicates that the
        port default, llcPortAdminInactTimer, shall be
        used as the SAP default.  This SAP default
        value may be overridden by a non-zero value in
        the llcCcAdminInactTimer.
        
        Any value for this object less than or equal to
        the acknowledgement timer shall mean that the
        timer is not used."
    DEFVAL { 0 }
    ::= { llcSapAdminEntry 10 }

llcSapAdminDelayAckCount OBJECT-TYPE
    SYNTAX Integer32
    ACCESS read-write
    STATUS mandatory
    DESCRIPTION
        "This object denotes the default value for the
        maximum number of consecutive I PDUs which the
        LLCs on this SAP shall receive during the
        interval defined by llcCcOperDelayTimer without
        sending an immediate acknowledgement.  This
        must be less than or equal to the value of
        llcCcOperMaxUnackIPDURcv. This function is not
        described in the IEEE 802.2 specification [5]
        but is widely implemented.
        
        A zero value for this object indicates that the
        port default, llcPortAdminDelayAck, shall be
        used as the SAP default.  This SAP default
        value may be overridden by a non-zero value in
        the llcCcAdminDelayAckCount.
        
        A value of one indicates that acknowledgments
        will be sent immediately and that the value of
        llcSapAdminDelayAckTimer shall be ignored."
    DEFVAL { 0 }
    ::= { llcSapAdminEntry 11 }

llcSapAdminDelayAckTimer OBJECT-TYPE
    SYNTAX TimeTicks
    ACCESS read-write
    STATUS mandatory
    DESCRIPTION
        "This object denotes the default value for the
        time interval during which the LLCs on this SAP
        shall delay acknowledgment of one or more I
        PDUs (up to the value of
        llcCcOperDelayAckCount). This function is not
        described in the IEEE 802.2 specification [5].
        
        It is listed in the IBM Token-Ring Network
        Architecture Reference [6] as the T2 parameter
        and is widely implemented.
        
        The expiration of this timer shall cause the
        local LLC to acknowledge all unacknowledged I
        PDUs.
        
        This object is associated with the
        llcSapAdminDelayAckCount object and is only
        defined if that object has a value greater than
        one."
    REFERENCE
        "IBM Token-Ring Network Architecture Ref. SC30-3374
         Chapter 11: Operation of Link Stations
         Receiver Acknowledgment Timer (T2)"
    DEFVAL { 0 }
    ::= { llcSapAdminEntry 12 }

llcSapAdminNw OBJECT-TYPE
    SYNTAX Integer32
    ACCESS read-write
    STATUS mandatory
    DESCRIPTION
        "This object denotes the default value for the
        number of IPDUs that must be acknowledged
        before the working window size (Ww) can be
        incremented by 1 when the working window is not
        equal to the maximum transmit window size (TW).
        It controls the gradual incrementing of Ww in
        congestion situations.
        
        This function is not described in the IEEE
        802.2 specification [5].  However, it is listed
        in the IBM Token-Ring Network Architecture
        Reference [6] as the Nw parameter and is widely
        implemented.
        
        This SAP default value may be overridden by a
        non-zero Cc default value in the llcCcAdminNw
        object."
    REFERENCE
        "IBM Token-Ring Network Architecture Ref.
        SC30-3374 Chapter 11: Operation of Link
        Stations Number of Acknowledgments Needed to
        Increment Ww (Nw)"
    ::= { llcSapAdminEntry 13 }

llcSapOperTable OBJECT-TYPE
    SYNTAX SEQUENCE OF LlcSapOperEntry
    ACCESS not-accessible
    STATUS mandatory
    DESCRIPTION
        "This table contains objects that reflect the
        current operational parameters of a local SAP."
    ::= { llcSapGroup 2 }

llcSapOperEntry OBJECT-TYPE
    SYNTAX LlcSapOperEntry
    ACCESS not-accessible
    STATUS mandatory
    DESCRIPTION
        "A list of configured values for a local SAP."
    INDEX { ifIndex, llcPortVirtualIndex, llcSapNumber }
    ::= { llcSapOperTable 1 }

LlcSapOperEntry ::= SEQUENCE {
    llcSapOperStatus INTEGER,
    llcSapOperNumCcs Integer32,
    llcSapOperHiWaterNumCcs Gauge32,
    llcSapOperLlc2Support INTEGER
    }

llcSapOperStatus OBJECT-TYPE
    SYNTAX INTEGER {
        inactive(1),
        active(2)
        }
    ACCESS read-only
    STATUS mandatory
    DESCRIPTION
        "This parameter describes the actual state of
        this local SAP."
    ::= { llcSapOperEntry 1 }

llcSapOperNumCcs OBJECT-TYPE
    SYNTAX Integer32
    ACCESS read-only
    STATUS mandatory
    DESCRIPTION
        "This object defines the number of connection
        components on this SAP that are currently in
        one of the 'connected' states.  In other words,
        this object is a count of the number of
        instances of llcCcOperEntry that have a
        llcCcOperState value greater than or equal to
        'normal(3)'."
    ::= { llcSapOperEntry 2 }

llcSapOperHiWaterNumCcs OBJECT-TYPE
    SYNTAX Gauge32
    ACCESS read-only
    STATUS mandatory
    DESCRIPTION
        "This object reflects the highest number of 
        connection components on this SAP simultaneously in
        one of the 'connected' states.  In other words,
        this object is a count of the number of
        instances of llcCcOperEntry that have a
        llcCcOperState value greater than or equal to
        'normal(3)' concurrently on this SAP."
    ::= { llcSapOperEntry 3 }

llcSapOperLlc2Support OBJECT-TYPE
    SYNTAX INTEGER {
        no(1),
        yes(2)
        }
    ACCESS read-only
    STATUS mandatory
    DESCRIPTION
        "This parameter describes whether or not the
        LLC implementation supports LLC2 connection
        components."
    ::= { llcSapOperEntry 4 }

llcSapStatsTable OBJECT-TYPE
    SYNTAX SEQUENCE OF LlcSapStatsEntry
    ACCESS not-accessible
    STATUS mandatory
    DESCRIPTION
        "This table contains objects that reflect the
        current operational parameters of a local SAP."
    ::= { llcSapGroup 3 }

llcSapStatsEntry OBJECT-TYPE
    SYNTAX LlcSapStatsEntry
    ACCESS not-accessible
    STATUS mandatory
    DESCRIPTION
        "A list of configured values for a local SAP."
    INDEX { ifIndex, llcPortVirtualIndex, llcSapNumber }
    ::= { llcSapStatsTable 1 }

LlcSapStatsEntry ::= SEQUENCE {
    llcSapStatsLocalBusies Counter32,
    llcSapStatsRemoteBusies Counter32,
    llcSapStatsIFramesIn Counter32,
    llcSapStatsIFramesOut Counter32,
    llcSapStatsIOctetsIn Counter32,
    llcSapStatsIOctetsOut Counter32,
    llcSapStatsSFramesIn Counter32,
    llcSapStatsSFramesOut Counter32,
    llcSapStatsRetransmitsOut Counter32,
    llcSapStatsREJsIn Counter32,
    llcSapStatsREJsOut Counter32,
    llcSapStatsWwCount Counter32,
    llcSapStatsTESTCommandsIn Counter32,
    llcSapStatsTESTCommandsOut Counter32,
    llcSapStatsTESTResponsesIn Counter32,
    llcSapStatsTESTResponsesOut Counter32,
    llcSapStatsXIDCommandsIn Counter32,
    llcSapStatsXIDCommandsOut Counter32,
    llcSapStatsXIDResponsesIn Counter32,
    llcSapStatsXIDResponsesOut Counter32,
    llcSapStatsUIFramesIn Counter32,
    llcSapStatsUIFramesOut Counter32,
    llcSapStatsUIOctetsIn Counter32,
    llcSapStatsUIOctetsOut Counter32,
    llcSapStatsConnectOk Counter32,
    llcSapStatsConnectFail Counter32,
    llcSapStatsDisconnect Counter32,
    llcSapStatsDisconnectFRMRSend Counter32,
    llcSapStatsDisconnectFRMRRcv Counter32,
    llcSapStatsDisconnectTimer Counter32,
    llcSapStatsDMsInABM Counter32,
    llcSapStatsSABMEsInABM Counter32
    }

llcSapStatsLocalBusies OBJECT-TYPE
    SYNTAX Counter32
    ACCESS read-only
    STATUS mandatory
    DESCRIPTION
        "This object reflects the total number of times
        that the local connection components on this
        SAP have entered a busy state (RNR).  This
        object is initialized to zero when the SAP is
        created."
    ::= { llcSapStatsEntry 1 }

llcSapStatsRemoteBusies OBJECT-TYPE
    SYNTAX Counter32
    ACCESS read-only
    STATUS mandatory
    DESCRIPTION
        "This object reflects the total number of
        times that the adjacent (i.e. remote) connection
        components on this SAP have entered a busy
        state (RNR).  This object is initialized to
        zero when the SAP is created."
    ::= { llcSapStatsEntry 2 }

llcSapStatsIFramesIn OBJECT-TYPE
    SYNTAX Counter32
    ACCESS read-only
    STATUS mandatory
    DESCRIPTION
        "This object reflects the total number of
        I-Frames that have been received by connection
        components on this SAP.  This object is
        initialized to zero when the SAP is created."
    ::= { llcSapStatsEntry 3 }

llcSapStatsIFramesOut OBJECT-TYPE
    SYNTAX Counter32
    ACCESS read-only
    STATUS mandatory
    DESCRIPTION
        "This object reflects the total number of
        I-Frames that have been transmitted by connection
        components on this SAP.  This object is
        initialized to zero when the SAP is created."
    ::= { llcSapStatsEntry 4 }

llcSapStatsIOctetsIn OBJECT-TYPE
    SYNTAX Counter32
    ACCESS read-only
    STATUS mandatory
    DESCRIPTION
        "This object reflects the total octets received
        from adjacent connection components on this
        SAP.  This object covers the address, control,
        and information field of I-Frames only.  This
        object is initialized to zero when the SAP is
        created."
    ::= { llcSapStatsEntry 5 }

llcSapStatsIOctetsOut OBJECT-TYPE
    SYNTAX Counter32
    ACCESS read-only
    STATUS mandatory
    DESCRIPTION
        "This object reflects the total octets
        transmitted to adjacent connection components
        on this SAP.  This object covers the address,
        control, and information field of I-Frames
        only.  This object is initialized to zero when
        the SAP is created."
    ::= { llcSapStatsEntry 6 }

llcSapStatsSFramesIn OBJECT-TYPE
    SYNTAX Counter32
    ACCESS read-only
    STATUS mandatory
    DESCRIPTION
        "This object reflects the total number of
        S-Frames that have been received by connection
        components on this SAP.  This object is
        initialized to zero when the SAP is created.
         Note - the ratio of the number of I-Frames to
        S-Frames might serve as a measure of link
        efficiency and, for instance, could be used to
        tune the acknowledgement timer."
    ::= { llcSapStatsEntry 7 }

llcSapStatsSFramesOut OBJECT-TYPE
    SYNTAX Counter32
    ACCESS read-only
    STATUS mandatory
    DESCRIPTION
        "This object reflects the total number of
        S-Frames that have been transmitted by connection
        components on this SAP.  This object is
        initialized to zero when the SAP is created.
        
        Note - the ratio of the number of I-Frames to
        S-Frames might serve as a measure of link
        efficiency and, for instance, could be used to
        tune the acknowledgement timer."
    ::= { llcSapStatsEntry 8 }

llcSapStatsRetransmitsOut OBJECT-TYPE
    SYNTAX Counter32
    ACCESS read-only
    STATUS mandatory
    DESCRIPTION
        "This object reflects the total number of
        I-Frames retransmitted by all local connection
        components on this SAP.  This object is
        initialized to zero when the SAP is created."
    ::= { llcSapStatsEntry 9 }

llcSapStatsREJsIn OBJECT-TYPE
    SYNTAX Counter32
    ACCESS read-only
    STATUS mandatory
    DESCRIPTION
        "This object reflects the total REJ frames
        received from all adjacent LLC connection
        components on this SAP since it was created."
    ::= { llcSapStatsEntry 10 }

llcSapStatsREJsOut OBJECT-TYPE
    SYNTAX Counter32
    ACCESS read-only
    STATUS mandatory
    DESCRIPTION
        "This object reflects the total REJ frames
        transmitted to an adjacent LLC connection
        components on this SAP since it was created."
    ::= { llcSapStatsEntry 11 }

llcSapStatsWwCount OBJECT-TYPE
    SYNTAX Counter32
    ACCESS read-only
    STATUS mandatory
    DESCRIPTION
        "This object reflects the total number of
        times, since this SAP was created, that the
        dynamic window algorithm has been invoked to
        reduce the value of Ww on any of the connection
        components of this SAP.  This object is
        initialized to zero when the SAP is created.
        
        This function is not described in the IEEE 802.2
        specification [5], but is widely implemented."
    ::= { llcSapStatsEntry 12 }

llcSapStatsTESTCommandsIn OBJECT-TYPE
    SYNTAX Counter32
    ACCESS read-only
    STATUS mandatory
    DESCRIPTION
        "This object denotes the number of TEST
        commands this SAP has received and is a measure
        of the number of stations in the network trying
        to connect up.
        
        This object is initialized to zero when the SAP
        is created."
    ::= { llcSapStatsEntry 13 }

llcSapStatsTESTCommandsOut OBJECT-TYPE
    SYNTAX Counter32
    ACCESS read-only
    STATUS mandatory
    DESCRIPTION
        "This object denotes the number of TEST
        commands this SAP has sent and is a measure of
        the number of other stations we are trying to
        connect to.
        
        This object is initialized to zero when the SAP
        is created."
    ::= { llcSapStatsEntry 14 }

llcSapStatsTESTResponsesIn OBJECT-TYPE
    SYNTAX Counter32
    ACCESS read-only
    STATUS mandatory
    DESCRIPTION
        "This object denotes the number of TEST
        responses this SAP has received and is a
        measure of the number of stations in the
        network responding to TEST commands this SAP
        has sent.
        
        This object is initialized to zero when the SAP
        is created."
    ::= { llcSapStatsEntry 15 }

llcSapStatsTESTResponsesOut OBJECT-TYPE
    SYNTAX Counter32
    ACCESS read-only
    STATUS mandatory
    DESCRIPTION
        "This object denotes the number of TEST
        responses this SAP has sent and is a measure of
        the number of other stations trying to connect
        to this SAP.
        
        This object is initialized to zero when the SAP
        is created."
    ::= { llcSapStatsEntry 16 }

llcSapStatsXIDCommandsIn OBJECT-TYPE
    SYNTAX Counter32
    ACCESS read-only
    STATUS mandatory
    DESCRIPTION
        "This object denotes the number of XID commands
        this SAP has received and is a measure of the
        number of stations in the network trying to
        connect to this SAP.  This object is a count of
        all XIDs, including SNA XID, IEEE XID, null
        XID, and non-activation XIDs.
        
        This object is initialized to zero when the SAP
        is created."
    ::= { llcSapStatsEntry 17 }

llcSapStatsXIDCommandsOut OBJECT-TYPE
    SYNTAX Counter32
    ACCESS read-only
    STATUS mandatory
    DESCRIPTION
        "This object denotes the number of XID commands
        this SAP has sent and is a measure of the
        number of other stations this SAP is trying to
        connect to.  This object is a count of all
        XIDs, including SNA XID, IEEE XID, null XID,
        and non-activation XIDs.
        
        This object is initialized to zero when the SAP
        is created."
    ::= { llcSapStatsEntry 18 }

llcSapStatsXIDResponsesIn OBJECT-TYPE
    SYNTAX Counter32
    ACCESS read-only
    STATUS mandatory
    DESCRIPTION
        "This object denotes the number of XID
        responses this SAP has received and is a
        measure of the number of stations in the
        network responding to TEST commands this SAP
        has sent.  This object is a count of all XIDs,
        including SNA XID, IEEE XID, null XID, and
        non-activation XIDs.
        
        This object is initialized to zero when the SAP
        is created."
    ::= { llcSapStatsEntry 19 }

llcSapStatsXIDResponsesOut OBJECT-TYPE
    SYNTAX Counter32
    ACCESS read-only
    STATUS mandatory
    DESCRIPTION
        "This object denotes the number of XID
        responses this SAP has sent and is a measure of
        the number of other stations trying to connect
        to this SAP.  This object is a count of all
        XIDs, including SNA XID, IEEE XID, null XID,
        and non-activation XIDs.
        
        This object is initialized to zero when the SAP
        is created."
    ::= { llcSapStatsEntry 20 }

llcSapStatsUIFramesIn OBJECT-TYPE
    SYNTAX Counter32
    ACCESS read-only
    STATUS mandatory
    DESCRIPTION
        "This object reflects the total number of
        unnumbered information (UI) frames received on
        a local SAP."
    ::= { llcSapStatsEntry 21 }

llcSapStatsUIFramesOut OBJECT-TYPE
    SYNTAX Counter32
    ACCESS read-only
    STATUS mandatory
    DESCRIPTION
        "This object reflects the total number of
        unnumbered information (UI) frames sent on a
        local SAP."
    ::= { llcSapStatsEntry 22 }

llcSapStatsUIOctetsIn OBJECT-TYPE
    SYNTAX Counter32
    ACCESS read-only
    STATUS mandatory
    DESCRIPTION
        "This object reflects the total octets received
        from adjacent connection components on this
        SAP.  This object covers the address, control,
        and information field of UI-Frames only.  This
        object is initialized to zero when the SAP is
        created."
    ::= { llcSapStatsEntry 23 }

llcSapStatsUIOctetsOut OBJECT-TYPE
    SYNTAX Counter32
    ACCESS read-only
    STATUS mandatory
    DESCRIPTION
        "This object reflects the total octets
        transmitted to adjacent connection components
        on this SAP.  This object covers the address,
        control, and information field of UI-Frames
        only.  This object is initialized to zero when
        the SAP is created."
    ::= { llcSapStatsEntry 24 }

llcSapStatsConnectOk OBJECT-TYPE
    SYNTAX Counter32
    ACCESS read-only
    STATUS mandatory
    DESCRIPTION
        "This object reflects the total number of
        successful connections that have been
        established on this SAP since the SAP was
        created.
        
        A successful connection is indicated by a
        successful SABME/UA exchange."
    ::= { llcSapStatsEntry 25 }

llcSapStatsConnectFail OBJECT-TYPE
    SYNTAX Counter32
    ACCESS read-only
    STATUS mandatory
    DESCRIPTION
        "This object reflects the total number of
        unsuccessful connections that have been
        attempted on this SAP since the SAP was
        created.
        
        An unsuccessful connection attempt is indicated
        by a SABME/DM exchange or a SABME/timeout."
    ::= { llcSapStatsEntry 26 }

llcSapStatsDisconnect OBJECT-TYPE
    SYNTAX Counter32
    ACCESS read-only
    STATUS mandatory
    DESCRIPTION
        "This object reflects the total number of
        normal disconnections that have been
        performed on this SAP since the SAP was
        created.
        
        A normal disconnection is indicated by a
        successful DISC/UA exchange or merely a DISC
        sent or received."
    ::= { llcSapStatsEntry 27 }

llcSapStatsDisconnectFRMRSend OBJECT-TYPE
    SYNTAX Counter32
    ACCESS read-only
    STATUS mandatory
    DESCRIPTION
        "This object reflects the total number of
        abnormal disconnections (resulting from a FRMR
        being sent) that have been performed on this
        SAP since the SAP was created."
    ::= { llcSapStatsEntry 28 }

llcSapStatsDisconnectFRMRRcv OBJECT-TYPE
    SYNTAX Counter32
    ACCESS read-only
    STATUS mandatory
    DESCRIPTION
        "This object reflects the total number of
        abnormal disconnections (resulting from a FRMR
        being received) that have been performed on
        this SAP since the SAP was created."
    ::= { llcSapStatsEntry 29 }

llcSapStatsDisconnectTimer OBJECT-TYPE
    SYNTAX Counter32
    ACCESS read-only
    STATUS mandatory
    DESCRIPTION
        "This object reflects the total number of
        abnormal disconnections (resulting from a timer
        expiration) that have been performed on this
        SAP since the SAP was created."
    ::= { llcSapStatsEntry 30 }

llcSapStatsDMsInABM OBJECT-TYPE
    SYNTAX Counter32
    ACCESS read-only
    STATUS mandatory
    DESCRIPTION
        "This object reflects the total number of
        Disconnect Mode responses that have been
        receveived for CCs in ABM mode on this SAP
        since the SAP was created."
    ::= { llcSapStatsEntry 31 }

llcSapStatsSABMEsInABM OBJECT-TYPE
    SYNTAX Counter32
    ACCESS read-only
    STATUS mandatory
    DESCRIPTION
        "This object reflects the total number of
        SABMEs that have been receveived for CCs in 
        already in ABM mode on this SAP since the SAP 
        was created."
    ::= { llcSapStatsEntry 32 }

llcCcAdminTable OBJECT-TYPE
    SYNTAX SEQUENCE OF LlcCcAdminEntry
    ACCESS not-accessible
    STATUS mandatory
    DESCRIPTION
        "This table contains objects that can be
        changed to manage an LLC connection component.
        Changing one of these parameters may take
        effect in the operating link immediately or may
        wait until the link is restarted depending on
        the details of the implementation.
        
        The entries in llcCcAdminTable can be created
        either by an agent or a management station. The
        management station can create an entry in
        llcCcAdminTable by setting the appropriate
        value in llcCcAdminRowStatus.
        
        Most of the objects in this read-create table
        have corresponding read-only objects in the
        llcCcOperTable that reflect the current
        operating value.
        
        The operating values may be different from
        these configured values if changed by XID
        negotiation or if a configured parameter was
        changed after the link was started."
    ::= { llcCcGroup 1 }

llcCcAdminEntry OBJECT-TYPE
    SYNTAX LlcCcAdminEntry
    ACCESS not-accessible
    STATUS mandatory
    DESCRIPTION
        "A list of configured values for an LLC connection
        component."
    INDEX { ifIndex, llcPortVirtualIndex, llcSapNumber, llcCcRMac, llcCcRSap }
    ::= { llcCcAdminTable 1 }

LlcCcAdminEntry ::= SEQUENCE {
    llcCcRMac MacAddress,
    llcCcRSap INTEGER,
    llcCcAdminBounce INTEGER,
    llcCcAdminMaxPDUOctets Integer32,
    llcCcAdminMaxUnackedIPDUsSend INTEGER,
    llcCcAdminMaxUnackedIPDUsRcv INTEGER,
    llcCcAdminMaxRetransmits Integer32,
    llcCcAdminAckTimer TimeTicks,
    llcCcAdminPbitTimer TimeTicks,
    llcCcAdminRejTimer TimeTicks,
    llcCcAdminBusyTimer TimeTicks,
    llcCcAdminInactTimer TimeTicks,
    llcCcAdminDelayAckCount Integer32,
    llcCcAdminDelayAckTimer TimeTicks,
    llcCcAdminNw Integer32,
    llcCcAdminRowStatus RowStatus
    }

llcCcRMac OBJECT-TYPE
    SYNTAX MacAddress
--    Rsyntax OCTET STRING(SIZE(6))
    ACCESS not-accessible
    STATUS mandatory
    DESCRIPTION
        "This value is the remote MAC address for this
        Connection Component. This value is provided
        by the SNMP agent."
    ::= { llcCcAdminEntry 1 }

llcCcRSap OBJECT-TYPE
    SYNTAX INTEGER(1..255)
    ACCESS not-accessible
    STATUS mandatory
    DESCRIPTION
        "This value is the address of the remote SAP
        for this Connection Component. This value
        is provided by the SNMP agent."
    ::= { llcCcAdminEntry 2 }

llcCcAdminBounce OBJECT-TYPE
    SYNTAX INTEGER {
        no(1),
        yes(2)
        }
    ACCESS read-write
    STATUS mandatory
    DESCRIPTION
        "This object controls the resetting of the
        connection component.  Setting this value to
        yes(2) results in the connection component
        being reset, llcCcOperState transitioning to a
        value of aDm(1), and the value of
        llcCcAdminBounce being set back to no(1)."
    DEFVAL { no }
    ::= { llcCcAdminEntry 3 }

llcCcAdminMaxPDUOctets OBJECT-TYPE
    SYNTAX Integer32
--  Units
--    octets
    ACCESS read-write
    STATUS mandatory
    DESCRIPTION
        "This object denotes the maximum I PDU size, in
        octets, that this LLC SAP may send to its
        remote connection component partner. This count
        is referred to as 'N1' in the IEEE 802.2
        specification [5].
        
        This object contains an administrative value
        which will be applied the next time this
        connection is established.  A zero value for
        this object indicates that the SAP default,
        llcSapAdminMaxIPDUOctetsSend, shall be used.
        
        At connection setup, the remote LLC may send,
        using an XID frame, the maximum I PDU size
        which it is prepared to receive. If so, an
        implementation may choose to override the
        administered maximum PDU size with the
        dynamically learned value and should reflect
        this in the llcCcOperMaxIPDUOctetsSend object
        for the connection component.
        
        The I PDU size includes all octets in a frame,
        excluding framing characters, the MAC header
        and link header."
    DEFVAL { 0 }
    ::= { llcCcAdminEntry 4 }

llcCcAdminMaxUnackedIPDUsSend OBJECT-TYPE
    SYNTAX INTEGER(0..127)
    ACCESS read-write
    STATUS mandatory
    DESCRIPTION
        "This object denotes the maximum consecutive
        unacknowledged I PDU frames that this LLC may
        send to its remote LLC partner. This count is
        referred to as 'k' in the IEEE 802.2
        specification [5].
        
        This object contains an administrative value
        which will be applied the next time this
        connection is established.  A zero value for
        this object indicates that the SAP default,
        llcSapAdminMaxUnackedIPDUsSend, shall be used.
        
        At connection setup, the remote LLC may send,
        using an XID frame, the maximum number of
        unacknowledged I PDUs which it is prepared to
        receive. If so, an implementation may choose to
        override the administered maximum number of
        unacknowledged PDUs with the dynamically learned
        value and should reflect this in the
        llcCcOperMaxUnackedIPDUsSend object for the
        connection component."
    DEFVAL { 0 }
    ::= { llcCcAdminEntry 5 }

llcCcAdminMaxUnackedIPDUsRcv OBJECT-TYPE
    SYNTAX INTEGER(0..127)
    ACCESS read-write
    STATUS mandatory
    DESCRIPTION
        "This object denotes the maximum number of
        unacknowledged I PDUs that this LLC can expect
        to receive from its remote LLC partner. This
        count is referred to as 'k' in the IEEE 802.2
        specification [5].
        
        This object contains an administrative value
        which will be applied the next time this
        connection is established.  A zero value for
        this object indicates that the SAP default,
        llcSapAdminMaxUnackedIPDUsRcv, shall be used.
        
        At connection setup, an implementation may
        choose to send this value to the remote LLC,
        using an XID frame."
    DEFVAL { 0 }
    ::= { llcCcAdminEntry 6 }

llcCcAdminMaxRetransmits OBJECT-TYPE
    SYNTAX Integer32
    ACCESS read-write
    STATUS mandatory
    DESCRIPTION
        "This object denotes the value for the maximum
        number of times that this LLC shall retry PDUs
        following the expiration of the acknowledgement
        timer, the P-bit timer or the reject timer.
        When these retries are exhausted, the link
        shall be declared inactive.  This count is
        referred to as 'N2' in the IEEE 802.2
        specification [5].
        
        This object contains an administrative value
        which will be applied the next time this
        connection is established.  A zero value for
        this object indicates that the SAP default,
        llcSapAdminMaxRetransmits, shall be used."
    DEFVAL { 0 }
    ::= { llcCcAdminEntry 7 }

llcCcAdminAckTimer OBJECT-TYPE
    SYNTAX TimeTicks
    ACCESS read-write
    STATUS mandatory
    DESCRIPTION
        "This object denotes the value for the time
        interval during which this LLC shall expect to
        receive either:
        
        1) an acknowledgement to one or more
        outstanding I PDUs.  or 2) a response PDU to an
        unnumbered command PDU.
        
        The expiration of this timer shall cause the
        frame unacknowledged frames to be retransmitted
        (up to N2 times).
        
        This object contains an administrative value
        which will be applied the next time this
        connection is established.  A zero value for
        this object indicates that the SAP default,
        llcSapAdminAckTimer, shall be used."
    DEFVAL { 0 }
    ::= { llcCcAdminEntry 8 }

llcCcAdminPbitTimer OBJECT-TYPE
    SYNTAX TimeTicks
    ACCESS read-write
    STATUS mandatory
    DESCRIPTION
        "This object denotes the value for the time
        interval during which this LLC shall expect to
        receive a PDU with the F bit set to '1' in
        response to a Type 2 command with the P bit set
        to '1'.
        
        The expiration of this timer shall cause the
        REJ PDU to be retransmitted (up to N2 times).
        
        This object contains an administrative value
        which will be applied the next time this
        connection is established.  A zero value for
        this object indicates that the SAP default,
        llcSapAdminPbitTimer, shall be used."
    DEFVAL { 0 }
    ::= { llcCcAdminEntry 9 }

llcCcAdminRejTimer OBJECT-TYPE
    SYNTAX TimeTicks
    ACCESS read-write
    STATUS mandatory
    DESCRIPTION
        "This object denotes the value for the time
        interval during which this LLC shall expect to
        receive a reply to a REJ PDU.
        
        The expiration of this timer shall cause the
        REJ PDU to be retransmitted (up to N2 times).
        
        This object contains an administrative value
        which will be applied the next time this
        connection is established.  A zero value for
        this object indicates that the SAP default,
        llcSapAdminRejTimer, shall be used."
    DEFVAL { 0 }
    ::= { llcCcAdminEntry 10 }

llcCcAdminBusyTimer OBJECT-TYPE
    SYNTAX TimeTicks
    ACCESS read-write
    STATUS mandatory
    DESCRIPTION
        "This object denotes the value for the time
        interval during which this LLC shall expect to
        receive an indication that a busy condition at
        the remote LLC has cleared.
        
        The expiration of this timer shall cause the
        link to be declared inactive.
        
        This object contains an administrative value
        which will be applied the next time this
        connection is established.  A zero value for
        this object indicates that the SAP default,
        llcSapAdminBusyTimer, shall be used."
    DEFVAL { 0 }
    ::= { llcCcAdminEntry 11 }

llcCcAdminInactTimer OBJECT-TYPE
    SYNTAX TimeTicks
    ACCESS read-write
    STATUS mandatory
    DESCRIPTION
        "This object denotes the value for the time
        interval during which this LLC shall expect to
        receive any PDU from the remote LLC.  This
        function is not described in the IEEE 802.2
        specification [5] but is widely implemented.
        
        The expiration of this timer shall cause the
        local LLC to send a PDU to the remote LLC with
        the P bit set to '1'.
        
        This object contains an administrative value
        which will be applied the next time this
        connection is established.  A zero value for
        this object indicates that the SAP default,
        llcSapAdminInactTimer, shall be used.
        
        Any value for this object less than or equal to
        the acknowledgement timer shall mean that the
        timer is not used."
    DEFVAL { 0 }
    ::= { llcCcAdminEntry 12 }

llcCcAdminDelayAckCount OBJECT-TYPE
    SYNTAX Integer32
    ACCESS read-write
    STATUS mandatory
    DESCRIPTION
        "This object denotes the value for the maximum
        number of consecutive I PDUs which this LLC
        shall receive during the interval defined by
        llcCcOperDelayTimer without sending an
        immediate acknowledgement.  This must be less
        than or equal to the value of
        llcCcOperMaxUnackIPDURcv. This function is not
        described in the IEEE 802.2 specification [5]
        but is widely implemented.
        
        This object contains an administrative value
        which will be applied the next time this
        connection is established.  A zero value for
        this object indicates that the SAP default,
        llcSapAdminDelayAck, shall be used.
        
        A value of one indicates that acknowledgments
        will be sent immediately and that the value of
        llcCcAdminDelayAckTimer shall be ignored."
    DEFVAL { 0 }
    ::= { llcCcAdminEntry 13 }

llcCcAdminDelayAckTimer OBJECT-TYPE
    SYNTAX TimeTicks
    ACCESS read-write
    STATUS mandatory
    DESCRIPTION
        "This object denotes the value for the time
        interval during which this LLC shall delay
        acknowledgment of one or more I PDUs (up to the
        value of llcCcOperDelayAckCount). This function
        is not described in the IEEE 802.2
        specification [5].
        
        It is listed in the IBM Token-Ring Network
        Architecture Reference [6] as the T2 parameter
        and is widely implemented.
        
        The expiration of this timer shall cause the
        local LLC to acknowledge all unacknowledged I
        PDUs.
        
        This object contains an administrative value
        which will be applied the next time this
        connection is established.
        
        This object is associated with the
        llcCcAdminDelayAckCount object and is only
        defined if that object has a value greater than
        one."
    REFERENCE
        "IBM Token-Ring Network Architecture Ref. SC30-3374
         Chapter 11: Operation of Link Stations
         Receiver Acknowledgment Timer (T2)"
    DEFVAL { 0 }
    ::= { llcCcAdminEntry 14 }

llcCcAdminNw OBJECT-TYPE
    SYNTAX Integer32
    ACCESS read-write
    STATUS mandatory
    DESCRIPTION
        "This object denotes the value for the number
        of IPDUs that must be acknowledged before the
        working window size (Ww) can be incremented by
        1 when the working window is not equal to the
        maximum transmit window size (TW). It controls
        the gradual incrementing of Ww in congestion
        situations.
        
        This function is not described in the IEEE
        802.2 specification [5].  However, it is listed
        in the IBM Token-Ring Network Architecture
        Reference [6] as the Nw parameter and is widely
        implemented."
    REFERENCE
        "IBM Token-Ring Network Architecture Ref.
        SC30-3374 Chapter 11: Operation of Link
        Stations Number of Acknowledgments Needed to
        Increment Ww (Nw)"
    ::= { llcCcAdminEntry 15 }

llcCcAdminRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used by a management station to
        create or delete the row entry in
        llcCcAdminTable following the RowStatus textual
        convention.
        
        Upon successful creation of the row, an agent
        automatically creates a corresponding entry in
        the llcCcOperTable with llcCcOperState equal to
        'aDM (1)'."
    ::= { llcCcAdminEntry 16 }

llcCcOperTable OBJECT-TYPE
    SYNTAX SEQUENCE OF LlcCcOperEntry
    ACCESS not-accessible
    STATUS mandatory
    DESCRIPTION
        "This table contains current LLC link
        parameters.  Many of these objects have
        corresponding objects in the
        llcCcAdminTable."
    ::= { llcCcGroup 2 }

llcCcOperEntry OBJECT-TYPE
    SYNTAX LlcCcOperEntry
    ACCESS not-accessible
    STATUS mandatory
    DESCRIPTION
        "A list of status and control values for an
        LLC connection component."
    INDEX { ifIndex, llcPortVirtualIndex, llcSapNumber, llcCcRMac, llcCcRSap }
    ::= { llcCcOperTable 1 }

LlcCcOperEntry ::= SEQUENCE {
    llcCcOperState INTEGER,
    llcCcOperMaxIPDUOctetsSend Integer32,
    llcCcOperMaxIPDUOctetsRcv Integer32,
    llcCcOperMaxUnackedIPDUsSend INTEGER,
    llcCcOperMaxUnackedIPDUsRcv INTEGER,
    llcCcOperMaxRetransmits Integer32,
    llcCcOperAckTimer TimeTicks,
    llcCcOperPbitTimer TimeTicks,
    llcCcOperRejTimer TimeTicks,
    llcCcOperBusyTimer TimeTicks,
    llcCcOperInactTimer TimeTicks,
    llcCcOperDelayAckCount Integer32,
    llcCcOperDelayAckTimer TimeTicks,
    llcCcOperNw Integer32,
    llcCcOperWw INTEGER,
    llcCcOperCreateTime TimeStamp,
    llcCcOperLastModifyTime TimeStamp,
    llcCcOperLastFailTime TimeStamp,
    llcCcOperLastFailCause INTEGER,
    llcCcOperLastFailFRMRInfo OCTET STRING,
    llcCcOperLastWwCause INTEGER
    }

llcCcOperState OBJECT-TYPE
    SYNTAX INTEGER {
        aDM(1),
        setup(2),
        normal(3),
        busy(4),
        reject(5),
        await(6),
        awaitBusy(7),
        awaitReject(8),
        dConn(9),
        reset(10),
        error(11),
        conn(12),
        resetCheck(13),
        resetWait(14)
        }
    ACCESS read-only
    STATUS mandatory
    DESCRIPTION
        "This object describes the operational state of
        the LLC connection.  If the connection component
        is disabled, llcCcOperState will transition to
        aDM(1).  If the connection component is enabled,
        llcCcOperState will transition to normal(3)."
    REFERENCE
        "ISO 8802-2 : 1989, ANSI/IEEE 802.2 - 1989
         Section 7.9.2.1.
         Connection Component State Descriptions"
    ::= { llcCcOperEntry 1 }

llcCcOperMaxIPDUOctetsSend OBJECT-TYPE
    SYNTAX Integer32
    ACCESS read-only
    STATUS mandatory
    DESCRIPTION
        "This object denotes the maximum I PDU size, in
        octets, that this LLC SAP may send to its
        remote connection component partner. This count
        is referred to as 'N1' in the IEEE 802.2
        specification [5].
        
        At connection setup, the remote LLC may send,
        using an XID frame, the maximum I PDU size
        which it is prepared to receive. If so, an
        implementation may choose to override the
        administered maximum PDU size with the
        dynamically learned value and should reflect
        that in this object.
        
        The I PDU size includes all octets in a frame,
        excluding framing characters, the MAC header
        and link header."
    ::= { llcCcOperEntry 2 }

llcCcOperMaxIPDUOctetsRcv OBJECT-TYPE
    SYNTAX Integer32
    ACCESS read-only
    STATUS mandatory
    DESCRIPTION
        "This object denotes the maximum I PDU size,in
        octets, that this LLC can expect to receive
        from its remote LLC partner. This count is
        referred to as 'N1' in the IEEE 802.2
        specification [5]
        
        The I PDU size includes all octets in a frame
        with the exception of the framing characters,
        the MAC header and the link header."
    ::= { llcCcOperEntry 3 }

llcCcOperMaxUnackedIPDUsSend OBJECT-TYPE
    SYNTAX INTEGER(1..127)
    ACCESS read-only
    STATUS mandatory
    DESCRIPTION
        "This object denotes the maximum consecutive
        unacknowledged I PDU frames that this LLC may
        send to its remote LLC partner. This count is
        referred to as 'k' in the IEEE 802.2
        specification [5].
        
        At connection setup, the remote LLC may send,
        using an XID frame, the maximum number of
        unacknowledged I PDUs which it is prepared to
        receive. If so, an implementation may choose to
        override the administered maximum number of
        unacknowledged PDUs with the dynamically learned
        value and should reflect that in this object."
    ::= { llcCcOperEntry 4 }

llcCcOperMaxUnackedIPDUsRcv OBJECT-TYPE
    SYNTAX INTEGER(1..127)
    ACCESS read-only
    STATUS mandatory
    DESCRIPTION
        "This object denotes the maximum number of
        unacknowledged I PDUs that this LLC can expect
        to receive from its remote LLC partner. This
        count is referred to as 'k' in the IEEE 802.2
        specification [5]."
    ::= { llcCcOperEntry 5 }

llcCcOperMaxRetransmits OBJECT-TYPE
    SYNTAX Integer32
    ACCESS read-only
    STATUS mandatory
    DESCRIPTION
        "This object denotes the value for the maximum
        number of times that this LLC shall retry PDUs
        following the expiration of the acknowledgement
        timer, the P-bit timer or the reject timer.
        When these retries are exhausted, the link
        shall be declared inactive.  This count is
        referred to as 'N2' in the IEEE 802.2
        specification [5]."
    ::= { llcCcOperEntry 6 }

llcCcOperAckTimer OBJECT-TYPE
    SYNTAX TimeTicks
    ACCESS read-only
    STATUS mandatory
    DESCRIPTION
        "This object denotes the value for the time
        interval during which this LLC shall expect to
        receive either:
        
        1) an acknowledgement to one or more
        outstanding I PDUs.  or 2) a response PDU to an
        unnumbered command PDU.
        
        The expiration of this timer shall cause the
        frame unacknowledged frames to be retransmitted
        (up to N2 times)."
    ::= { llcCcOperEntry 7 }

llcCcOperPbitTimer OBJECT-TYPE
    SYNTAX TimeTicks
    ACCESS read-only
    STATUS mandatory
    DESCRIPTION
        "This object denotes the value for the time
        interval during which this LLC shall expect to
        receive a PDU with the F bit set to '1' in
        response to a Type 2 command with the P bit set
        to '1'.
        
        The expiration of this timer shall cause the
        REJ PDU to be retransmitted (up to N2 times)."
    ::= { llcCcOperEntry 8 }

llcCcOperRejTimer OBJECT-TYPE
    SYNTAX TimeTicks
    ACCESS read-only
    STATUS mandatory
    DESCRIPTION
        "This object denotes the value for the time
        interval during which this LLC shall expect to
        receive a reply to a REJ PDU.
        
        The expiration of this timer shall cause the
        REJ PDU to be retransmitted (up to N2 times)."
    ::= { llcCcOperEntry 9 }

llcCcOperBusyTimer OBJECT-TYPE
    SYNTAX TimeTicks
    ACCESS read-only
    STATUS mandatory
    DESCRIPTION
        "This object denotes the value for the time
        interval during which this LLC shall expect to
        receive an indication that a busy condition at
        the remote LLC has cleared.
        
        The expiration of this timer shall cause the
        link to be declared inactive."
    ::= { llcCcOperEntry 10 }

llcCcOperInactTimer OBJECT-TYPE
    SYNTAX TimeTicks
    ACCESS read-only
    STATUS mandatory
    DESCRIPTION
        "This object denotes the value for the time
        interval during which this LLC shall expect to
        receive any PDU from the remote LLC.  This
        function is not described in the IEEE 802.2
        specification [5] but is widely implemented.
        
        The expiration of this timer shall cause the
        local LLC to send a PDU to the remote LLC with
        the P bit set to '1'.
        
        Any value for this object less than or equal to
        the acknowledgement timer shall mean that the
        timer is not used."
    ::= { llcCcOperEntry 11 }

llcCcOperDelayAckCount OBJECT-TYPE
    SYNTAX Integer32
    ACCESS read-only
    STATUS mandatory
    DESCRIPTION
        "This object denotes the value for the maximum
        number of consecutive I PDUs which this LLC
        shall receive during the interval defined by
        llcCcOperDelayTimer without sending an
        immediate acknowledgement.  This must be less
        than or equal to the value of
        llcCcOperMaxUnackIPDURcv. This function is not
        described in the IEEE 802.2 specification [5]
        but is widely implemented.
        
        A value of one indicates that acknowledgments
        will be sent immediately and that the value of
        llcCcOperDelayAckTimer should be ignored."
    ::= { llcCcOperEntry 12 }

llcCcOperDelayAckTimer OBJECT-TYPE
    SYNTAX TimeTicks
    ACCESS read-only
    STATUS mandatory
    DESCRIPTION
        "This object denotes the value for the time
        interval during which this LLC shall delay
        acknowledgment of one or more I PDUs (up to the
        value of llcCcOperDelayAckCount). This function
        is not described in the IEEE 802.2
        specification [5] but is widely implemented.
        
        The expiration of this timer shall cause the
        local LLC to acknowledge all unacknowledged I
        PDUs.
        
        This object is associated with the
        llcCcOperDelayAckCount object and only has
        meaning if that object has a value greater than
        one."
    ::= { llcCcOperEntry 13 }

llcCcOperNw OBJECT-TYPE
    SYNTAX Integer32
    ACCESS read-only
    STATUS mandatory
    DESCRIPTION
        "This object denotes the value for the number
        of IPDUs that must be acknowledged before the
        working window size (Ww) can be incremented by
        1 when the working window is not equal to the
        maximum transmit window size (TW). It controls
        the gradual incrementing of Ww in congestion
        situations.
        
        This function is not described in the IEEE
        802.2 specification [5], but is widely
        implemented."
    REFERENCE
        "IBM Token-Ring Network Architecture Ref.
        SC30-3374 Chapter 11: Operation of Link
        Stations Number of Acknowledgments Needed to
        Increment Ww (Nw)"
    ::= { llcCcOperEntry 14 }

llcCcOperWw OBJECT-TYPE
    SYNTAX INTEGER(1..127)
    ACCESS read-only
    STATUS mandatory
    DESCRIPTION
        "Maximum number of sequentially numbered IPDUs
        that the connection component may have
        outstanding (unacknowledged) at any given time.
        Ww is initialized to the value of
        llcCcOperMaxUnackedIPDUsSend when the link is
        established. When the dynamic window algorithm
        is invoked, Ww varies from 1 up to
        llcCcOperMaxUnackedIPDUsSend.
        
        Each time the llcCcOperWw value is decreased,
        the reason is recorded in llcCcOperLastWwCause,
        and llcCcStatWwCount is incremented by 1.
        
        This function is not described in the IEEE
        802.2 specification [5], but is widely
        implemented."
    REFERENCE
        "IBM Token-Ring Network Architecture Ref.
        SC30-3374 Chapter 8: LLC Frames Working Window
        Size, Ww"
    ::= { llcCcOperEntry 15 }

llcCcOperCreateTime OBJECT-TYPE
    SYNTAX TimeStamp
--    Rsyntax TimeTicks
    ACCESS read-only
    STATUS mandatory
    DESCRIPTION
        "This object describes the value of sysUpTime
         when this connection was created."
    ::= { llcCcOperEntry 16 }

llcCcOperLastModifyTime OBJECT-TYPE
    SYNTAX TimeStamp
--    Rsyntax TimeTicks
    ACCESS read-only
    STATUS mandatory
    DESCRIPTION
        "This object describes the value of sysUpTime
         the last time this connection component was
         modified.  If the connection has not been
         modified, then this value shall be zero."
    ::= { llcCcOperEntry 17 }

llcCcOperLastFailTime OBJECT-TYPE
    SYNTAX TimeStamp
--    Rsyntax TimeTicks
    ACCESS read-only
    STATUS mandatory
    DESCRIPTION
        "This object describes the value of sysUpTime
         when this LLC connection component last
         failed.  If the connection component has not failed,
         then this value shall be zero."
    ::= { llcCcOperEntry 18 }

llcCcOperLastFailCause OBJECT-TYPE
    SYNTAX INTEGER {
        undefined(1),
        rxFRMR(2),
        txFRMR(3),
        discReceived(4),
        discSent(5),
        retriesExpired(6),
        forcedShutdown(7)
        }
    ACCESS read-only
    STATUS mandatory
    DESCRIPTION
        "This enumerated object reflects the cause of
        the last failure of this LLC connection
        component.  If the connection component has not
        failed, then this object will have a value of
        undefined(1)."
    DEFVAL { undefined }
    ::= { llcCcOperEntry 19 }

llcCcOperLastFailFRMRInfo OBJECT-TYPE
    SYNTAX OCTET STRING(SIZE(3))
    ACCESS read-only
    STATUS mandatory
    DESCRIPTION
        "This object reflects the information field of
        the FRMR frame if the last failure for this LLC
        connection component was as a result of an
        invalid frame.  Otherwise, this field has no
        meaning."
    ::= { llcCcOperEntry 20 }

llcCcOperLastWwCause OBJECT-TYPE
    SYNTAX INTEGER {
        neverInvoked(1),
        lostData(2),
        macLayerCongestion(3),
        other(4)
        }
    ACCESS read-only
    STATUS mandatory
    DESCRIPTION
        "This object indicates the reason that the llcCcOperWw
        was reduced the last time this occurred."
    REFERENCE
        "IBM Token-Ring Network Architecture Ref. SC30-3374
        Chapter 11: Operation of Link Stations
        The Dynamic Window Algorithm."
    ::= { llcCcOperEntry 21 }

llcCcStatsTable OBJECT-TYPE
    SYNTAX SEQUENCE OF LlcCcStatsEntry
    ACCESS not-accessible
    STATUS mandatory
    DESCRIPTION
        "Each entry in this table contains statistics
        for a specific LLC connection component."
    ::= { llcCcGroup 3 }

llcCcStatsEntry OBJECT-TYPE
    SYNTAX LlcCcStatsEntry
    ACCESS not-accessible
    STATUS mandatory
    DESCRIPTION
        "A list of statistics for an LLC connection
        component."
    INDEX { ifIndex, llcPortVirtualIndex, llcSapNumber, llcCcRMac, llcCcRSap }
    ::= { llcCcStatsTable 1 }

LlcCcStatsEntry ::= SEQUENCE {
    llcCcStatsLocalBusies Counter32,
    llcCcStatsRemoteBusies Counter32,
    llcCcStatsIFramesIn Counter32,
    llcCcStatsIFramesOut Counter32,
    llcCcStatsIOctetsIn Counter32,
    llcCcStatsIOctetsOut Counter32,
    llcCcStatsSFramesIn Counter32,
    llcCcStatsSFramesOut Counter32,
    llcCcStatsRetransmitsOut Counter32,
    llcCcStatsREJsIn Counter32,
    llcCcStatsREJsOut Counter32,
    llcCcStatsWwCount Counter32
    }

llcCcStatsLocalBusies OBJECT-TYPE
    SYNTAX Counter32
    ACCESS read-only
    STATUS mandatory
    DESCRIPTION
        "This object reflects the total number of times
        that the local connection component has entered
        a busy state (RNR).  This object is initialized
        to zero when the connection component is
        created."
    ::= { llcCcStatsEntry 1 }

llcCcStatsRemoteBusies OBJECT-TYPE
    SYNTAX Counter32
    ACCESS read-only
    STATUS mandatory
    DESCRIPTION
        "This object reflects the total number of times
        that the adjacent (i.e. remote) connection
        component has entered a busy state (RNR).  This
        object is initialized to zero when the
        connection component is created."
    ::= { llcCcStatsEntry 2 }

llcCcStatsIFramesIn OBJECT-TYPE
    SYNTAX Counter32
    ACCESS read-only
    STATUS mandatory
    DESCRIPTION
        "This object reflects the total number of
        I-Frames that have been received by the
        connection component.  This object is
        initialized to zero when the connection
        component is created."
    ::= { llcCcStatsEntry 3 }

llcCcStatsIFramesOut OBJECT-TYPE
    SYNTAX Counter32
    ACCESS read-only
    STATUS mandatory
    DESCRIPTION
        "This object reflects the total number of
        I-Frames that have been transmitted by this
        connection component.  This object is
        initialized to zero when the connection
        component is created."
    ::= { llcCcStatsEntry 4 }

llcCcStatsIOctetsIn OBJECT-TYPE
    SYNTAX Counter32
    ACCESS read-only
    STATUS mandatory
    DESCRIPTION
        "This object reflects the total octets received
        from the adjacent connection component.  This
        object covers the address, control, and
        information field of I-Frames only.  This
        object is initialized to zero when the
        connection component is created."
    ::= { llcCcStatsEntry 5 }

llcCcStatsIOctetsOut OBJECT-TYPE
    SYNTAX Counter32
    ACCESS read-only
    STATUS mandatory
    DESCRIPTION
        "This object reflects the total octets
        transmitted to the adjacent connection
        component.  This object covers the address,
        control, and information field of I-Frames
        only.  This object is initialized to zero when
        the connection component is created."
    ::= { llcCcStatsEntry 6 }

llcCcStatsSFramesIn OBJECT-TYPE
    SYNTAX Counter32
    ACCESS read-only
    STATUS mandatory
    DESCRIPTION
        "This object reflects the total number of
        S-Frames that have been received by this
        connection component.  This object is
        initialized to zero when the connection
        component is created.
        
        Note - the ratio of the number of I-Frames to
        S-Frames might serve as a measure of link
        efficiency and, for instance, could be used to
        tune the acknowledgement timer."
    ::= { llcCcStatsEntry 7 }

llcCcStatsSFramesOut OBJECT-TYPE
    SYNTAX Counter32
    ACCESS read-only
    STATUS mandatory
    DESCRIPTION
        "This object reflects the total number of
        S-Frames that have been transmitted by this
        connection component.  This object is
        initialized to zero when the connection
        component is created.
        
        Note - the ratio of the number of I-Frames to
        S-Frames might serve as a measure of link
        efficiency and, for instance, could be used to
        tune the acknowledgement timer."
    ::= { llcCcStatsEntry 8 }

llcCcStatsRetransmitsOut OBJECT-TYPE
    SYNTAX Counter32
    ACCESS read-only
    STATUS mandatory
    DESCRIPTION
        "This object reflects the total number of
        I-Frames retransmitted the local connection
        component.  This object is initialized to zero
        when the connection component is created."
    ::= { llcCcStatsEntry 9 }

llcCcStatsREJsIn OBJECT-TYPE
    SYNTAX Counter32
    ACCESS read-only
    STATUS mandatory
    DESCRIPTION
        "This object reflects the total REJ frames
        received from an adjacent LLC connection
        component since connection component startup."
    ::= { llcCcStatsEntry 10 }

llcCcStatsREJsOut OBJECT-TYPE
    SYNTAX Counter32
    ACCESS read-only
    STATUS mandatory
    DESCRIPTION
        "This object reflects the total REJ frames
        transmitted to an adjacent LLC connection
        component since connection component startup."
    ::= { llcCcStatsEntry 11 }

llcCcStatsWwCount OBJECT-TYPE
    SYNTAX Counter32
    ACCESS read-only
    STATUS mandatory
    DESCRIPTION
        "This object reflects the total number of times, since
        connection component startup, that the dynamic window
        algorithm has been invoked to reduce the value of Ww.
        At connection component startupm this object must be
        initialized to zero.
        
        This function is not described in the IEEE 802.2
        specification [5], but is widely implemented."
    ::= { llcCcStatsEntry 12 }

llcCcStatusChange TRAP-TYPE
-- Reverse mappable trap
    ENTERPRISE snaLlcMIBNotificationPrefix
    VARIABLES {
        llcCcOperState, llcCcOperLastFailTime, 
        llcCcOperLastFailCause, llcCcOperLastFailFRMRInfo }
--  Status
--    mandatory
    DESCRIPTION
        "This trap indicates that the state of an LLC
         connection component has transitioned to
         normal(3) or aDM(1)."
    ::= 1

llcCorePortGroup OBJECT IDENTIFIER ::= { snaLlcMIBGroups 1 }
-- OBJECT-GROUP
--  Status
--    mandatory
--  Descr
--    The llcCorePortGroup defines objects
--    which are common to the LLC Port of all
--    compliant connections.
--  objects
--    llcPortAdminName, llcPortAdminMaxSaps, llcPortAdminMaxCcs, 
--    llcPortAdminMaxPDUOctets, llcPortAdminMaxUnackedIPDUsSend, 
--    llcPortAdminMaxUnackedIPDUsRcv, llcPortAdminMaxRetransmits, 
--    llcPortAdminAckTimer, llcPortAdminPbitTimer, 
--    llcPortAdminRejTimer, llcPortAdminBusyTimer, 
--    llcPortAdminInactTimer, llcPortAdminDelayAckCount, 
--    llcPortAdminDelayAckTimer, llcPortAdminNw, 
--    llcPortOperMacAddress, llcPortOperNumSaps, 
--    llcPortOperHiWaterNumSaps, llcPortOperSimRim, 
--    llcPortOperLastModifyTime, llcPortStatsPDUsIn, 
--    llcPortStatsPDUsOut, llcPortStatsOctetsIn, 
--    llcPortStatsOctetsOut, llcPortStatsTESTCommandsIn, 
--    llcPortStatsTESTResponsesOut, llcPortStatsLocalBusies, 
--    llcPortStatsUnknownSaps

llcCoreSapGroup OBJECT IDENTIFIER ::= { snaLlcMIBGroups 2 }
-- OBJECT-GROUP
--  Status
--    mandatory
--  Descr
--    The llcCoreSapGroup defines objects
--    which are common to the LLC SAP of all
--    compliant connections.
--  objects
--    llcSapAdminMaxPDUOctets, llcSapAdminMaxUnackedIPDUsSend, 
--    llcSapAdminMaxUnackedIPDUsRcv, llcSapAdminMaxRetransmits, 
--    llcSapAdminAckTimer, llcSapAdminPbitTimer, 
--    llcSapAdminRejTimer, llcSapAdminBusyTimer, 
--    llcSapAdminInactTimer, llcSapAdminDelayAckCount, 
--    llcSapAdminDelayAckTimer, llcSapAdminNw, llcSapOperStatus, 
--    llcSapOperNumCcs, llcSapOperHiWaterNumCcs, 
--    llcSapOperLlc2Support, llcSapStatsLocalBusies, 
--    llcSapStatsRemoteBusies, llcSapStatsIFramesIn, 
--    llcSapStatsIFramesOut, llcSapStatsIOctetsIn, 
--    llcSapStatsIOctetsOut, llcSapStatsSFramesIn, 
--    llcSapStatsSFramesOut, llcSapStatsRetransmitsOut, 
--    llcSapStatsREJsIn, llcSapStatsREJsOut, llcSapStatsWwCount, 
--    llcSapStatsTESTCommandsIn, llcSapStatsTESTCommandsOut, 
--    llcSapStatsTESTResponsesIn, llcSapStatsTESTResponsesOut, 
--    llcSapStatsXIDCommandsIn, llcSapStatsXIDCommandsOut, 
--    llcSapStatsXIDResponsesIn, llcSapStatsXIDResponsesOut, 
--    llcSapStatsUIFramesIn, llcSapStatsUIFramesOut, 
--    llcSapStatsUIOctetsIn, llcSapStatsUIOctetsOut, 
--    llcSapStatsConnectOk, llcSapStatsConnectFail, 
--    llcSapStatsDisconnect, llcSapStatsDisconnectFRMRSend, 
--    llcSapStatsDisconnectFRMRRcv, llcSapStatsDisconnectTimer, 
--    llcSapStatsDMsInABM, llcSapStatsSABMEsInABM

llcCoreCcGroup OBJECT IDENTIFIER ::= { snaLlcMIBGroups 3 }
-- OBJECT-GROUP
--  Status
--    mandatory
--  Descr
--    The llcCoreCcGroup defines objects
--    which are common to the LLC CC of all
--    compliant connections.
--  objects
--    llcCcAdminBounce, llcCcAdminMaxPDUOctets, 
--    llcCcAdminMaxUnackedIPDUsSend, llcCcAdminMaxUnackedIPDUsRcv, 
--    llcCcAdminMaxRetransmits, llcCcAdminAckTimer, 
--    llcCcAdminPbitTimer, llcCcAdminRejTimer, llcCcAdminBusyTimer, 
--    llcCcAdminInactTimer, llcCcAdminDelayAckCount, 
--    llcCcAdminDelayAckTimer, llcCcAdminNw, llcCcAdminRowStatus, 
--    llcCcOperState, llcCcOperMaxIPDUOctetsSend, 
--    llcCcOperMaxIPDUOctetsRcv, llcCcOperMaxUnackedIPDUsSend, 
--    llcCcOperMaxUnackedIPDUsRcv, llcCcOperMaxRetransmits, 
--    llcCcOperAckTimer, llcCcOperPbitTimer, llcCcOperRejTimer, 
--    llcCcOperBusyTimer, llcCcOperInactTimer, 
--    llcCcOperDelayAckCount, llcCcOperDelayAckTimer, llcCcOperNw, 
--    llcCcOperWw, llcCcOperCreateTime, llcCcOperLastModifyTime, 
--    llcCcOperLastFailTime, llcCcOperLastFailCause, 
--    llcCcOperLastFailFRMRInfo, llcCcOperLastWwCause, 
--    llcCcStatsLocalBusies, llcCcStatsRemoteBusies, 
--    llcCcStatsIFramesIn, llcCcStatsIFramesOut, 
--    llcCcStatsIOctetsIn, llcCcStatsIOctetsOut, 
--    llcCcStatsSFramesIn, llcCcStatsSFramesOut, 
--    llcCcStatsRetransmitsOut, llcCcStatsREJsIn, llcCcStatsREJsOut, 
--    llcCcStatsWwCount

llcCoreCompliance OBJECT IDENTIFIER ::= { snaLlcMIBCompliances 1 }
-- MODULE-COMPLIANCE
--  Status
--    mandatory
--  Descr
--    The core compliance statement for all LLC nodes.
--  Module
--    >>current<<
--   MandGroup
--    llcCorePortGroup
--   MandGroup
--    llcCoreSapGroup
--   MandGroup
--    llcCoreCcGroup
--   ObjVar
--    llcPortAdminName
--   ObjVar
--    llcPortAdminMaxSaps
--   ObjVar
--    llcPortAdminMaxCcs
--   ObjVar
--    llcPortAdminMaxPDUOctets
--   ObjVar
--    llcPortAdminMaxUnackedIPDUsSend
--   ObjVar
--    llcPortAdminMaxRetransmits
--   ObjVar
--    llcPortAdminAckTimer
--   ObjVar
--    llcPortAdminPbitTimer
--   ObjVar
--    llcPortAdminRejTimer
--   ObjVar
--    llcPortAdminBusyTimer
--   ObjVar
--    llcPortAdminInactTimer
--   ObjVar
--    llcPortAdminDelayAckCount
--   ObjVar
--    llcPortAdminDelayAckTimer
--   ObjVar
--    llcPortAdminNw
--   ObjVar
--    llcSapAdminMaxPDUOctets
--   ObjVar
--    llcSapAdminMaxUnackedIPDUsSend
--   ObjVar
--    llcSapAdminMaxRetransmits
--   ObjVar
--    llcSapAdminAckTimer
--   ObjVar
--    llcSapAdminPbitTimer
--   ObjVar
--    llcSapAdminRejTimer
--   ObjVar
--    llcSapAdminBusyTimer
--   ObjVar
--    llcSapAdminInactTimer
--   ObjVar
--    llcSapAdminDelayAckCount
--   ObjVar
--    llcSapAdminDelayAckTimer
--   ObjVar
--    llcSapAdminNw


END
