DECHUB900-HRIP DEFINITIONS ::= BEGIN

--
--  Definitions of Managed Objects for Digital Equipment Corperations's
--                  DEChub900 Ring Insertion Process (HRIP)
--                  =======================================
--
--
--                 Name:    dechub900-hrip-mib-v1-1.mib
--                 Version: 1.1
--                 Date:    May, 1994
--                 Company: Digital Equipment Corperations
--                 Mail:    hub900-support@lkg.dec.com
--
--
--  
--
--  
--  This Digital Equipment  Corporation  SNMP  Management  Information  Base
--  Specification  embodies Digital Equipment Corporation's confidential and
--  proprietary  intellectual  property.   Digital   Equipment   Corporation
--  retains  all  title  and  ownership  in the Specification, including any
--  revisions.
--  
--  It is Digital Equipment Corporation's intent to encourage the widespread
--  use  of  this Specification in connection with the management of Digital
--  Equipment Corporation products.
--  
--  Digital Equipment  Corporation  grants  vendors,  end-users,  and  other
--  interested  parties a non-exclusive license to use this Specification in
--  connection  with  the  management  of  Digital   Equipment   Corporation
--  products.
--  
--  Digital Equipment Corporation reserves the right to make changes in this
--  specification  and  other information contained in this document without
--  prior notice.
--  
--  Digital Equipment Corporation makes no  warranty,  either  expressed  or
--  implied,  as  to  the  use,  operation, condition, or performance of the
--  Specification.  In no  event  shall  Digital  Equipment  Corporation  be
--  liable  for  any incidental, indirect, special, or consequential damages
--  whatsoever (including but not limited to loss of profits) arising out of
--  or related to this document or the information contained in it.
--
--
--  
--
--  
--
--
--  1  Status of This Memo
--
--  This MIB module provides definitions for Digital Equipment Corporation's
--  DEChub900 MultiSwich Hub Ring Insertion Process (HRIP).
--
--  Digital offers Internet anonymous ftp access to DEChub900 MIBs from 
--  gatekeeper.dec.com.
--
--      1)  Use the Internet application "ftp" to connect to 
--          gatekeeper.dec.com (Internet address 16.1.0.2).
--      2)  Log in as user "anonymous".
--      3)  Use you electronic mail address as the password.
--      4)  Change directories to the /pub/DEC/hub900/mibs area using
--          "cd /pub/DEC/hub900/mibs".
--      5)  Use the "ascii" command to specify that you are 
--          retrieving ASCII test files.
--      6)  Get the README file using "get README".
--      7)  The README file explains how to retrieve this MIB.
--          It lists the latest version on the MIB.  It may
--          instruct you to "cd" to another directory where
--          you can "get" this MIB.
--      8)  When you are finished, use the "quit" command to log out.
--
--  Inquiries about the contents and use of this MIB may be sent to 
--  hub900-support@lkg.dec.com.
--
--
--
--  2  Relationship to Other MIBs
--
--
--  The  objects  defined  in  this   MIB   are   located   under   the
--  private.enterprises subtree as shown below:
--
--                    iso(1).org(3).dod(6).internet(1)
--                                 |
--                              private(4)
--                                 |
--                              enterprises(1)
--                                 |
--                              dec(36)
--                                 |
--                              ema(2)
--                                 |
--                              decMIBextension(18)
--                                 |
--                              decHub900(11)
--                                 |
--                     .___________.___________.___________// ...etc...
--                     |                       |
--                mgmtAgent(1)              common(2) 
--                     |                       |
--                mgmtAgentVersion1(1)      ...ect...
--                     |
--       ._____________._____________._____________.
--       |             |             |             |
--       |        .___________.      |             |
--   chassis(1)   |  hrip(2)  |    hubIp(3)     hubAuthCreate(4)
--                |___________|
--
--
--
--  3  Abstract
--
--  This MIB contains definitions for the DEChub900 Ring Insertion Process.
--
--
--
--
--  4  References
--
--
--  [1]  RFC 1213.  McCloghrie, K., and M. Rose, "Management Information Base 
--       for Network Management of TCP/IP-based Internets".  March, 1991.
--
--  [2]  RFC 1155.  Rose, M., and K. McCloghrie, "Structure and Identification 
--       of Management Information for TCP/IP-based Internets".  May, 1990.
--
--  [3]  DEChub 900 MultiSwitch Owner's Manual.  Digital Equipment 
--       Corp.  Order number:  EK-DH2MS-OM.<version>.
--
--
--
--
--  5  Object Synopsis
--  
--
--
--  Object Name                             Object ID            Non-Vol
--  =================================       =================    ========
--  hrip                                    p.2
--    hripPubRingCfgTable                   p.2.1
--      hripPubRingCfgEntry                 p.2.1.1
--        hripRingIndex                     p.2.1.1.1.n
--        hripRingCfgSpeed                  p.2.1.1.2.n            yes
--    hripPubSlotCfgTable                   p.2.2
--      hripPubSlotCfgEntry                 p.2.2.1
--        hripSlotIndex                     p.2.2.1.1.n
--        hripSlotCfgDisable                p.2.2.1.2.n            yes
--        hripSlotCfgForce                  p.2.2.1.3.n            yes
--    hripPubRingStatTable                  p.2.3
--      hripPubRingStatEntry                p.2.3.1
--        hripRingIndex                     p.2.3.1.1.n
--        hripRingStatNumModInserted        p.2.3.1.2.n
--    hripPubSlotStatTable                  p.2.4
--      hripPubSlotStatEntry                p.2.4.1
--        hripSlotIndex                     p.2.4.1.1.n
--        hripSlotStatRingAInsertCount      p.2.4.1.2.n
--        hripSlotStatRingBInsertCount      p.2.4.1.3.n
--        hripSlotStatTcuA                  p.2.4.1.4.n
--        hripSlotStatTcuB                  p.2.4.1.5.n
--
--  where p is:  iso(1).org(3).dod(6).internet(1).private(4)
--                   enterprises(1).dec(36).ema(2).decMIBextension(18)
--                   decHub900(11).mgmtAgent(1).mgmtAgentVersion1(1)
--
--  and n is the instance of the tabular object.
--

IMPORTS
    Gauge, enterprises
        FROM RFC1155-SMI
    OBJECT-TYPE
        FROM RFC-1212;

--  Path to the Hub Ring Insertion Process MIB.

dec                 OBJECT IDENTIFIER ::= { enterprises 36 }
ema                 OBJECT IDENTIFIER ::= { dec 2 }
decMIBextension     OBJECT IDENTIFIER ::= { ema 18 }
decHub900           OBJECT IDENTIFIER ::= { decMIBextension 11 }
mgmtAgent           OBJECT IDENTIFIER ::= { decHub900 1 }
mgmtAgentVersion1   OBJECT IDENTIFIER ::= { mgmtAgent 1 }

--  The Hub Ring Insertion Process MIB.

hrip OBJECT IDENTIFIER ::= { mgmtAgentVersion1 2 }

--
--  Ring Configuration Table
--

hripPubRingCfgTable OBJECT-TYPE
    SYNTAX  SEQUENCE OF HripPubRingCfgEntry  
    ACCESS  not-accessible
    STATUS  mandatory
    DESCRIPTION
        "Defines a table for ring speeds.  The table has 2 rows.  Row 1
         defines ring speed for ring A and row 2 defines the ring speed
         for ring B."
    ::= { hrip 1 }

hripPubRingCfgEntry OBJECT-TYPE 
    SYNTAX  HripPubRingCfgEntry 
    ACCESS  not-accessible
    STATUS  mandatory
    DESCRIPTION 
        "An entry in the hripPubRingCfgTable."
    INDEX {hripRingCfgIndex}
    ::= { hripPubRingCfgTable 1 }

HripPubRingCfgEntry ::=
      SEQUENCE {
          hripRingCfgIndex 
              INTEGER,
          hripRingCfgSpeed
              INTEGER
          }

hripRingCfgIndex OBJECT-TYPE 
    SYNTAX  INTEGER {
                ringA(1),
                ringB(2) 
                }
    ACCESS  read-only
    STATUS  mandatory
    DESCRIPTION 
        "Identifies the ring being accessed ie the row of the table 
         being referred to."
    ::= { hripPubRingCfgEntry 1 }

hripRingCfgSpeed OBJECT-TYPE
    SYNTAX  INTEGER {
                speed4(2),
                speed16(3)
                }
    ACCESS  read-write
    STATUS  mandatory
    DESCRIPTION
        "The speed of each of the token rings on the backplane.
         speed4(1) indicates a speed of 4 Mbits per second while
         speed16(2) indicates 16 Mbits per second.

         The value of this object is maintained across power cycles
         and resets."
    ::= { hripPubRingCfgEntry 2 }

--
--  Slot Configuration Table
--

hripPubSlotCfgTable OBJECT-TYPE
    SYNTAX  SEQUENCE OF HripPubSlotCfgEntry
    ACCESS  not-accessible
    STATUS  mandatory
    DESCRIPTION
        "Defines a table for Slot Configurations.  Each row in the table 
         corresponds to a backplane slot (hripSlotIndex)."
    ::= { hrip 2 }

hripPubSlotCfgEntry OBJECT-TYPE
    SYNTAX  HripPubSlotCfgEntry
    ACCESS  not-accessible
    STATUS  mandatory
    DESCRIPTION
        "An entry in the hripPubSlotCfgTable."
    INDEX { hripSlotCfgIndex }
    ::= { hripPubSlotCfgTable 1 }

HripPubSlotCfgEntry ::=
    SEQUENCE {
        hripSlotCfgIndex
            INTEGER,
        hripSlotCfgDisable
            INTEGER,
        hripSlotCfgForce
            INTEGER
        }

hripSlotCfgIndex OBJECT-TYPE 
    SYNTAX  INTEGER (1..65535)
    ACCESS  read-only
    STATUS  mandatory
    DESCRIPTION
        "Index into the table of slot configurations."
    ::= { hripPubSlotCfgEntry 1 }

hripSlotCfgDisable OBJECT-TYPE
    SYNTAX  INTEGER {
                enabled(1),      
                disabled(2)
                }
    ACCESS  read-write
    STATUS  mandatory
    DESCRIPTION
        "Locks out the entire slot of the backplane.  Sets of this
         object to disable(2) cause the hub TCU for both rings of 
         the slot to be wrapped, until this variable is reset to
         enabled(1).

         The value of this object is maintained across power cycles
         and resets."
    ::= { hripPubSlotCfgEntry 2 }

hripSlotCfgForce OBJECT-TYPE
    SYNTAX  INTEGER {
                noForce(1),      -- no forcing by NOC
                forceRingA(2),   -- force to speed of Ring A
                forceRingB(3)    -- force to speed of Ring B
                }
    ACCESS  read-write
    STATUS  mandatory
    DESCRIPTION
        "Describes a slot/ring pairing.

         The value of this object is maintained across power cycles
         and resets."
    ::= { hripPubSlotCfgEntry 3 }               

--
--  Ring status table.
-- 
--  These objects are used by NMS to monitor status of TR Insertion
--  Process.
--

hripPubRingStatTable OBJECT-TYPE
    SYNTAX  SEQUENCE OF HripPubRingStatEntry 
    ACCESS  not-accessible
    STATUS  mandatory
    DESCRIPTION 
        "A table describing the number of modules on each ring."
    ::= { hrip 3 }

hripPubRingStatEntry OBJECT-TYPE
    SYNTAX  HripPubRingStatEntry
    ACCESS  not-accessible
    STATUS  mandatory
    DESCRIPTION
        "An entry describing the number of modules on each ring."
    INDEX { hripRingStatIndex }
    ::= { hripPubRingStatTable 1 }

HripPubRingStatEntry ::=
    SEQUENCE {
        hripRingStatIndex
            INTEGER,
        hripRingStatNumModInserted
            INTEGER
        }

hripRingStatIndex OBJECT-TYPE 
    SYNTAX  INTEGER {
                ringA (1),
                ringB (2)
                }
    ACCESS  read-only
    STATUS  mandatory
    DESCRIPTION 
        "An index into the hripPubRingStatTable."
    ::= { hripPubRingStatEntry 1 }

hripRingStatNumModInserted OBJECT-TYPE 
    SYNTAX  INTEGER (1..65535)
    ACCESS  read-only
    STATUS  mandatory
    DESCRIPTION 
        "The number of modules inserted onto the ring."
    ::= { hripPubRingStatEntry 2 }

--
--  Slot Status Table.
-- 

hripPubSlotStatTable OBJECT-TYPE
    SYNTAX  SEQUENCE OF HripPubSlotStatEntry
    ACCESS  not-accessible
    STATUS  mandatory
    DESCRIPTION 
        "The status of modules inserted on each slot of backplane."
    ::= { hrip 4 }

hripPubSlotStatEntry OBJECT-TYPE 
    SYNTAX  HripPubSlotStatEntry
    ACCESS  not-accessible
    STATUS  mandatory
    DESCRIPTION
        "An entry in the hripPubSlotStatTable."
    INDEX { hripSlotStatIndex }
    ::= { hripPubSlotStatTable 1 }

HripPubSlotStatEntry ::=
    SEQUENCE {
        hripSlotStatIndex
            INTEGER,
        hripSlotStatRingAInsertCount
            Gauge,
        hripSlotStatRingBInsertCount
            Gauge,
        hripSlotStatTcuA
            INTEGER,
        hripSlotStatTcuB
            INTEGER
      }

hripSlotStatIndex OBJECT-TYPE 
    SYNTAX  INTEGER (1..8)
    ACCESS  read-only
    STATUS  mandatory
    DESCRIPTION
        "The index into slot status table."
    ::= { hripPubSlotStatEntry 1 }

hripSlotStatRingAInsertCount OBJECT-TYPE
    SYNTAX  Gauge
    ACCESS  read-only
    STATUS  mandatory
    DESCRIPTION
        "The number of times that the module has transitioned 
         between inserted/wrapped states on backplane ring A, 
         since the module was last reset/power-cycled."
    ::= { hripPubSlotStatEntry 2 }

hripSlotStatRingBInsertCount OBJECT-TYPE
    SYNTAX  Gauge
    ACCESS  read-only
    STATUS  mandatory
    DESCRIPTION
        "The number of times that the module has transitioned 
         between inserted/wrapped states on backplane ring B, 
         since the module was last reset/power-cycled."
    ::= { hripPubSlotStatEntry 3 }

hripSlotStatTcuA OBJECT-TYPE
    SYNTAX  INTEGER {
                inserted(1),
                wrapped(2)
                }
     ACCESS  read-only
     STATUS  mandatory
     DESCRIPTION
         "Status of the TCU on ring A."
     ::= { hripPubSlotStatEntry 4 }

hripSlotStatTcuB OBJECT-TYPE
    SYNTAX  INTEGER {
                inserted(1),
                wrapped(2)
                }
    ACCESS  read-only
    STATUS  mandatory
    DESCRIPTION
        "Status of the TCU on ring B."
    ::= { hripPubSlotStatEntry 5 }

END
