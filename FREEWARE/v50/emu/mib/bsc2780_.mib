-- Version 1.2.1.4, modified 3/23/94

          BSC2780-OPT-MIB DEFINITIONS ::= BEGIN

          IMPORTS
                  mgmt, NetworkAddress, IpAddress, Counter, Gauge,
                          TimeTicks
                      FROM RFC1155-SMI
                  OBJECT-TYPE
                          FROM RFC-1212

                  cdx6500PCTPortProtocolGroup,
                  cdx6500PSTPortProtocolGroup
                  FROM CDX6500-SMI;


          --  This MIB module uses the extended OBJECT-TYPE macro as
          --  defined in [14];



          -- textual conventions

          DisplayString ::=
              OCTET STRING
          -- This data type is used to model textual information taken
          -- from the NVT ASCII character set.  By convention, objects
          -- with this syntax are declared as having
          --
          --      SIZE (0..255)

          PhysAddress ::=
              OCTET STRING
          -- This data type is used to model media addresses.  For many
          -- types of media, this will be in a binary representation.
          -- For example, an ethernet address would be represented as
          -- a string of 6 octets.

          -- BSC2780 MIB STARTS FROM HERE:


          -- The BSC2780 group contains the configuration parameters,
          -- statistics, and control objects used by the BSC2780
          -- ports and devices.

          -- BSC2780 Port Configuration Table

          cdx6500PPCTBSC2780Table OBJECT-TYPE
              SYNTAX  SEQUENCE OF Cdx6500Bsc2780PortConfigEntry
              ACCESS  not-accessible
              STATUS  mandatory
              DESCRIPTION
                      "A table of BSC2780 Port configuration entries."
              ::= {cdx6500PCTPortProtocolGroup 11  }

          cdx6500bsc2780PortConfigEntry OBJECT-TYPE
              SYNTAX  Cdx6500Bsc2780PortConfigEntry
              ACCESS  not-accessible
              STATUS  mandatory
              DESCRIPTION
                      "A BSC2780 Configuration Table entry. Each entry
                       contains the configuration parameters for a single
                       BSC2780 port. "
              INDEX   { cdx6500bsc2780PortNumber }
              ::= {cdx6500PPCTBSC2780Table 1 }

          Cdx6500Bsc2780PortConfigEntry ::=
              SEQUENCE {
          cdx6500bsc2780PortNumber 
                 INTEGER, 
          cdx6500bsc2780ClockSource 
                 INTEGER,
          cdx6500bsc2780ClockSpeed 
                 INTEGER,
          cdx6500bsc2780Contention 
                 INTEGER,
          cdx6500bsc2780ErrThreshCount 
                 INTEGER,
          cdx6500bsc2780DisConnOnError
                 INTEGER,
          cdx6500bsc2780ConnType 
                 INTEGER,
          cdx6500bsc2780InterBuffTimeout 
                 INTEGER,
          cdx6500bsc2780PortSubAddr 
                 DisplayString,
	  cdx6500bsc2780ReConnRetry 
                 INTEGER,
          cdx6500bsc2780AutocallMnemonic 
                 DisplayString,
    	  cdx6500bsc2780RestrictConnDest 
                 DisplayString, 
          cdx6500bsc2780BillRec 
                 INTEGER,
          cdx6500bsc2780DSRfollowSVC 
                 INTEGER,
          cdx6500bsc2780DSRholdTime 
                 INTEGER,
	      cdx6500bsc2780PortOption 
                 INTEGER,
          cdx6500bsc2780TrafficPriority
                 INTEGER,
	      cdx6500bsc2780PortOptString 
                 DisplayString
                     }

          cdx6500bsc2780PortNumber OBJECT-TYPE
              SYNTAX  INTEGER (1..54)
              ACCESS  read-only
              STATUS  mandatory
              DESCRIPTION
                      "The BSC2780 port number described by this entry"
              ::= { cdx6500bsc2780PortConfigEntry 1 }

          cdx6500bsc2780ClockSource OBJECT-TYPE
              SYNTAX  INTEGER {
                                int(0),
                                ext(1)
                              }
              ACCESS  read-only
              STATUS  mandatory
              DESCRIPTION
                      "int - internal clock source
                       ext - external clock source"
              DEFVAL { ext }
              ::= { cdx6500bsc2780PortConfigEntry 2 }

          cdx6500bsc2780ClockSpeed OBJECT-TYPE
              SYNTAX  INTEGER (1200..19200)
              ACCESS  read-only
              STATUS  mandatory
              DESCRIPTION
                      "This is the speed of the port in bits per second,
                       when using internal clocking."
              DEFVAL { 4800 }
              ::= { cdx6500bsc2780PortConfigEntry 3 }

          cdx6500bsc2780Contention OBJECT-TYPE
              SYNTAX  INTEGER {
                                hdx(0),
                                fdx(1)
                              }
              ACCESS  read-only
              STATUS  mandatory
              DESCRIPTION
                      "Indicates whether Half Duplex (hdx) or
                       Full Duplex (fdx) modem signals are being generated. 
                       Full Duplex indicates communication is occuring
                       in both directions simultaneously between devices.
                       Half Duplex indicates transmission is occuring
                       in both directions, but only in one direction
                       at a time."
              DEFVAL { fdx }
              ::= { cdx6500bsc2780PortConfigEntry 4 }


          cdx6500bsc2780ErrThreshCount OBJECT-TYPE
              SYNTAX  INTEGER (1..255)
              ACCESS  read-only
              STATUS  mandatory
              DESCRIPTION
                      "Indicates number of consecutive errors that can occur
                       before a device is considered down."
              DEFVAL { 5 }
              ::= { cdx6500bsc2780PortConfigEntry 5 }

        cdx6500bsc2780DisConnOnError OBJECT-TYPE
              SYNTAX  INTEGER {
                                no(0),
                                yes(1)
                              }
              ACCESS  read-only
              STATUS  mandatory
              DESCRIPTION
                      "Specifies whether a session should be disconnected if a control unit
                       has not responded once the Error Threshold Count has been exceeded."

              DEFVAL { yes }
		::= { cdx6500bsc2780PortConfigEntry 6 }
        
	      cdx6500bsc2780ConnType OBJECT-TYPE
              SYNTAX  INTEGER {
                               simp (0),
                               rs366 (14),
                               v25b (13)
                              }
              ACCESS  read-only
              STATUS  mandatory
              DESCRIPTION
                      "Specify the control signal handshake required for a
                       connection to be made to this port:
                        simp  - simple, no control signals required
                        v25b - port emulates a dial modem using V.25 bis mode 108/2
                        rs366 - port emulates data port for the 801 autodialer"

              DEFVAL { 0 }
		::= { cdx6500bsc2780PortConfigEntry 7 }

          cdx6500bsc2780InterBuffTimeout OBJECT-TYPE
              SYNTAX  INTEGER (1..255)
              ACCESS  read-only
              STATUS  mandatory
              DESCRIPTION
                      "Specifies the maximum amount of time in seconds the PAD
                       will wait for the end of a multi-packet message from the
                       network. If this time limit is exceeded, the PAD will
                       abort the entire message and request retransmission."
              DEFVAL { 30 }
              ::= { cdx6500bsc2780PortConfigEntry 8 }


          cdx6500bsc2780PortSubAddr OBJECT-TYPE
              SYNTAX  DisplayString (SIZE(0..3))
              ACCESS  read-only
              STATUS  mandatory
              DESCRIPTION
                      "0 - 3 Decimal digits
                       Calls addressed to this node and with this subaddress
                       will be routed to this port."
              ::= { cdx6500bsc2780PortConfigEntry 9 }


	      cdx6500bsc2780ReConnRetry OBJECT-TYPE
              SYNTAX  INTEGER (0..255)
              ACCESS  read-only
              STATUS  mandatory
              DESCRIPTION
                      "Number of times connection will be reattempted after a network induced
                       disconnect."
              DEFVAL { 10 }
              ::= { cdx6500bsc2780PortConfigEntry 10 }

          cdx6500bsc2780AutocallMnemonic OBJECT-TYPE
              SYNTAX  DisplayString (SIZE(0..8))
              ACCESS  read-only
              STATUS  mandatory
              DESCRIPTION
                      "This mnemonic name is used if this device is configured as a
                       call originator."
  		      ::= {  cdx6500bsc2780PortConfigEntry 11 }

    	  cdx6500bsc2780RestrictConnDest OBJECT-TYPE
              SYNTAX  DisplayString (SIZE(0..32))
              ACCESS  read-only
              STATUS  mandatory
              DESCRIPTION
                      "All calls originating from this port will be routed to the destination
                       specified in this parameter, irrespective of route selection table
                       entries.  For example, to route calls to port 1, use P1.  To route
                       calls to port 2, station 4, use P2S4.  Blank this field to disable
                       this function."
		::= {  cdx6500bsc2780PortConfigEntry 12 }

          cdx6500bsc2780BillRec OBJECT-TYPE
              SYNTAX  INTEGER {
				off(0),
				on(1)
                              }
              ACCESS  read-only
              STATUS  mandatory
              DESCRIPTION
                      "This controls whether billing (accounting) records will be created for
                       calls on this port."
              DEFVAL { off }
              ::= { cdx6500bsc2780PortConfigEntry 13 }

          cdx6500bsc2780DSRfollowSVC OBJECT-TYPE
              SYNTAX  INTEGER {
                                no(0),
                                yes(1)
                              }
              ACCESS  read-only
              STATUS  mandatory
              DESCRIPTION
                      "Specify whether DSR on/off required with circuit on/off.
                       This is only available with connection type SIMP or RS366.
                          yes = DSR will be ON only while a call is in place,
                                The DTE connected to the port can not originate a call
                          no = DSR is always ON."
              DEFVAL { no }
		::= { cdx6500bsc2780PortConfigEntry 14 }

	      cdx6500bsc2780DSRholdTime OBJECT-TYPE
              SYNTAX  INTEGER (50..3000)
              ACCESS  read-only
              STATUS  mandatory
              DESCRIPTION
                      "Time in steps of 50 ms to drop DSR signal after
                       the circuit is disconnected in DSR_Follow_SVC mode.
                       This timer value is ignored otherwise. "
              DEFVAL { 250 }
		::= { cdx6500bsc2780PortConfigEntry 15 }

	      cdx6500bsc2780PortOption OBJECT-TYPE
              SYNTAX  INTEGER {
                                none(0),
                                eot(1)
                              } 
              ACCESS  read-only
              STATUS  deprecated
              DESCRIPTION
                      " This object has been deprecated, according to RFC1155 (the SYNTAX of the 
                        object can not be changed)
                        It is replaced by cdx6500bsc2780PortOptString."
              DEFVAL { 0 }
		::= { cdx6500bsc2780PortConfigEntry 16 }

	      cdx6500bsc2780TrafficPriority OBJECT-TYPE
              SYNTAX  INTEGER {
				lowPriority(0),
				medPriority(1),
				hiPriority(2),
                                xpPriority(3)
                              } 
              ACCESS  read-only
              STATUS  optional
              DESCRIPTION
                      "This is the traffic priority of the 2780 device; low, medium, high,
                       and expedite. "
              DEFVAL { medPriority }
		::= { cdx6500bsc2780PortConfigEntry 17 }

	      cdx6500bsc2780PortOptString OBJECT-TYPE
              SYNTAX  DisplayString (SIZE(3..16))
              ACCESS  read-only
              STATUS  mandatory
              DESCRIPTION
                      " This is the new object for cdx6500bsc2780PortOption.

                        Specify any of the following port control options:
                        eot   - EOT will be dropped when no data has been sent across network.
                        none  - none"
              DEFVAL { none }
		::= { cdx6500bsc2780PortConfigEntry 18 }



          -- BSC2780 Port Statistics

          cdx6500PPSTBSC2780Table  OBJECT-TYPE
              SYNTAX  SEQUENCE OF Cdx6500Bsc2780PortStatEntry
              ACCESS  not-accessible
              STATUS  mandatory
              DESCRIPTION
                      "A table of BSC2780 port statistics entries."
              ::= { cdx6500PSTPortProtocolGroup 11 }

          cdx6500bsc2780PortStatEntry OBJECT-TYPE
              SYNTAX  Cdx6500Bsc2780PortStatEntry
              ACCESS  not-accessible
              STATUS  mandatory
              DESCRIPTION
                      "A BSC2780 Port Statistic Table entry. Each entry
                       contains the statistics for a single BSC2780
                       port. "
              INDEX   { cdx6500bsc2780StatPortNumber }
              ::= { cdx6500PPSTBSC2780Table 1 }

         Cdx6500Bsc2780PortStatEntry ::=
              SEQUENCE {
                  cdx6500bsc2780StatPortNumber
                      INTEGER,
                  cdx6500bsc2780PortStatus
                      INTEGER,
                  cdx6500bsc2780PortState
                      DisplayString,
                  cdx6500bsc2780PortSpeed
                      INTEGER,
                  cdx6500bsc2780PortUtilIn
                      INTEGER,
                  cdx6500bsc2780PortUtilOut
                      INTEGER,
                  cdx6500bsc2780InMsgs
                      Counter,
                  cdx6500bsc2780OutMsgs
                      Counter,
                  cdx6500bsc2780InChars
                      Counter,
                  cdx6500bsc2780OutChars
                      Counter,
                  cdx6500bsc2780CharRateIn
                      INTEGER,
                  cdx6500bsc2780CharRateOut
                      INTEGER,
                  cdx6500bsc2780CrcBccErrs
                      Counter
          }

          cdx6500bsc2780StatPortNumber OBJECT-TYPE
              SYNTAX  INTEGER (1..54)
              ACCESS  read-only
              STATUS  mandatory
              DESCRIPTION
                      "The BSC2780 port number described by this entry"
              ::= { cdx6500bsc2780PortStatEntry 1 }

          cdx6500bsc2780PortStatus OBJECT-TYPE
              SYNTAX  INTEGER {
                                disabled(0),
                                enabled(1),
                                busyOut(2),
                                up(3),
                                down(4)
                              }
              ACCESS  read-only
              STATUS  mandatory
              DESCRIPTION
                      "Port Status indicates whether or not the port
                       is switched on and is ready for operation. This value
                       may be one of :

                        up - Port is up and running
                        down - port is down
                        disabled - port has been disabled
                        enabled - port has been enabled, but is not yet Up
                        busyOut - port has been set to be disabled as soon as
                                  last active session is disestablished. No
                                  new sessions will be established"
              DEFVAL { disabled }
              ::= { cdx6500bsc2780PortStatEntry 2 }

          cdx6500bsc2780PortState OBJECT-TYPE
              SYNTAX  DisplayString (SIZE(4..10))
              ACCESS  read-only
              STATUS  mandatory
              DESCRIPTION
                      "Port State indicates what the port is actually in the
                       process of doing. This value may be one of :

                        INACTIVE - H/TPAD port inactive entered during boot
                        WTPOLSERVE - TPAD is waiting for response to a poll
                        WTSELRESP - TPAD is waiting for the response to a
                                    select
                        WTDATARESP - H/TPAD is waiting for data to be
                                     acknowledged
                        DATA - H/TPAD is in the process of sending/receiving
                               data
                        SEL/POL - TPAD is about to select or poll a
                                  controller. This is the most common state
                                  for a TPAD
                        SELECT - TPAD is about to select a device
                        POLL - TPAD is about to poll a device
                        WTENQRESP - H/TPAD is waiting for a NAK response to
                                    an ENQ sent
                        IDLE - HPAD is waiting for the host to send commands.
                               This is the most common state of the HPAD
                        WTEOT - HPAD is waiting for an expected EOT from the
                                host
                        FLUSHINGDATA - HPAD encountered an error in the message
                                       received from the host. As a result, 
                                       the data is being flushed
                        WTLCM - HPAD received a read/modify and is waiting for
                                the response from the TPAD."
              ::= { cdx6500bsc2780PortStatEntry 3 }

          cdx6500bsc2780PortSpeed OBJECT-TYPE
              SYNTAX  INTEGER
              ACCESS  read-only
              STATUS  mandatory
              DESCRIPTION
                      "This is the speed of the port if clock is internal. If
                       clock is external, this is the detected clock speed. If
                       Port Speed is 0, clock is external, but clocking is not
                       being received from attatched device."
              DEFVAL { 4800 }
              ::= { cdx6500bsc2780PortStatEntry 4 }

          cdx6500bsc2780PortUtilIn OBJECT-TYPE
              SYNTAX  INTEGER (0..100)
              ACCESS  read-only
              STATUS  mandatory
              DESCRIPTION
                      "Pertcentage of Port input bandwidth in use."
              DEFVAL { 0 }
              ::= { cdx6500bsc2780PortStatEntry 5 }

          cdx6500bsc2780PortUtilOut OBJECT-TYPE
              SYNTAX  INTEGER (0..100)
              ACCESS  read-only
              STATUS  mandatory
              DESCRIPTION
                      "Pertcentage of Port output bandwidth in use."
              ::= { cdx6500bsc2780PortStatEntry 6 }

          cdx6500bsc2780InMsgs OBJECT-TYPE
              SYNTAX  Counter
              ACCESS  read-only
              STATUS  mandatory
              DESCRIPTION
                      "Number of message received since last node, port, or
                       statistics reset."

              ::= { cdx6500bsc2780PortStatEntry 7 }

          cdx6500bsc2780OutMsgs OBJECT-TYPE
              SYNTAX  Counter
              ACCESS  read-only
              STATUS  mandatory
              DESCRIPTION
                      "Number of message sent since last node, port, or
                       statistics reset."
              ::= { cdx6500bsc2780PortStatEntry 8 }

          cdx6500bsc2780InChars OBJECT-TYPE
              SYNTAX  Counter
              ACCESS  read-only
              STATUS  mandatory
              DESCRIPTION
                      "Number of characters received since last node, port, or
                      statistics reset."
              ::= { cdx6500bsc2780PortStatEntry 9 }

          cdx6500bsc2780OutChars OBJECT-TYPE
              SYNTAX  Counter
              ACCESS  read-only
              STATUS  mandatory
              DESCRIPTION
                      "Number of characters sent since last node, port, or
                      statistics reset."
              ::= { cdx6500bsc2780PortStatEntry 10 }

          cdx6500bsc2780CharRateIn OBJECT-TYPE
              SYNTAX  INTEGER (0..65535)
              ACCESS  read-only
              STATUS  mandatory
              DESCRIPTION
                      "Number of characters received per second"

              ::= { cdx6500bsc2780PortStatEntry 11 }

          cdx6500bsc2780CharRateOut OBJECT-TYPE
              SYNTAX  INTEGER (0..65535)
              ACCESS  read-only
              STATUS  mandatory
              DESCRIPTION
                      "Number of characters sent per second"

              ::= { cdx6500bsc2780PortStatEntry 12 }

          cdx6500bsc2780CrcBccErrs OBJECT-TYPE
              SYNTAX  Counter
              ACCESS  read-only
              STATUS  mandatory
              DESCRIPTION
                      "Number of CRC errors since last node, port, or
                       statistics reset."
              ::= { cdx6500bsc2780PortStatEntry 13 }



	END
