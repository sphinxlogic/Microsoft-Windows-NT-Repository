-- Request for Comments: Draft             cisco Systems, Inc.


                                -- cisco Trap MIB

                                -- Mon Nov 18 1991


                              -- cisco Systems, Inc.
                                 -- 1525 O'Brien
                             -- Menlo Park, CA  94025

                          -- customer-service@cisco.com



          -- 1. Introduction

          -- This memo describes the snmp traps that are implemented for
          -- the cisco Systems, Inc.  set of products including the
          -- Gateway Server, Terminal Server, Trouter, and Protocol
          -- Translator.  The document relies upon the Structure of
          -- Management Information (SMI), RFC1155.  It is presented in
          -- a format described in RFC1215.

    CISCOTRAP-MIB DEFINITIONS ::= BEGIN

          IMPORTS
              sysUpTime, ifIndex, ifDescr, ifType, egpNeighAddr,
              tcpConnState
                   FROM RFC1213-MIB
              cisco, whyReload, locIfReason, authAddr, tslineSesType,
              loctcpConnElapsed, loctcpConnInBytes, loctcpConnOutBytes,
              tsLineUser
                   FROM CISCO-MIB
              TRAP-TYPE
                   FROM RFC-1215;

               products            OBJECT IDENTIFIER ::= { cisco 1 }
               local               OBJECT IDENTIFIER ::= { cisco 2 }
               temporary           OBJECT IDENTIFIER ::= { cisco 3 }

               gateway-server      OBJECT IDENTIFIER ::= { products 1 }
               terminal-server     OBJECT IDENTIFIER ::= { products 2 }
               trouter             OBJECT IDENTIFIER ::= { products 3 }
               protocol-translator OBJECT IDENTIFIER ::= { products 4 }
               igs                 OBJECT IDENTIFIER ::= { products 5 }

               lsystem             OBJECT IDENTIFIER ::= { local 1 }
               linterfaces         OBJECT IDENTIFIER ::= { local 2 }
               lat                 OBJECT IDENTIFIER ::= { local 3 }
               lip                 OBJECT IDENTIFIER ::= { local 4 }
               licmp               OBJECT IDENTIFIER ::= { local 5 }
               ltcp                OBJECT IDENTIFIER ::= { local 6 }
               ludp                OBJECT IDENTIFIER ::= { local 7 }
               legp                OBJECT IDENTIFIER ::= { local 8 }
               lts                 OBJECT IDENTIFIER ::= { local 9 }

               decnet              OBJECT IDENTIFIER ::= { temporary 1 }
               xns                 OBJECT IDENTIFIER ::= { temporary 2 }
               appletalk           OBJECT IDENTIFIER ::= { temporary 3 }
               novell              OBJECT IDENTIFIER ::= { temporary 4 }
               vines               OBJECT IDENTIFIER ::= { temporary 5 }




 -- Cisco Private Enterprise Traps

          reload TRAP-TYPE
              ENTERPRISE  igs
              VARIABLES   { sysUpTime, whyReload }
              DESCRIPTION
                          "A reload trap signifies that the sending
                          protocol entity is reinitializing itself such
                          that the agent's configuration or the protocol
                          entity implementation may be altered."
                        --#TYPE "Cisco router reload"
                        --#SUMMARY "Router manually reloaded from the Priveledged prompt"
                        --#ARGUMENTS {0}
                        --#SEVERITY CRITICAL
                        --#TIMEINDEX 0
                        --#STATE NONOPERATIONAL
              ::= 0

          tcpConnectionClose TRAP-TYPE
              ENTERPRISE  igs
              VARIABLES   { tslineSesType, tcpConnState,
                            loctcpConnElapsed, loctcpConnInBytes,
                            loctcpConnOutBytes, tsLineUser }
              DESCRIPTION
                          "A tty trap signifies that a TCP connection,
                          previously established with the sending
                          protocol entity for the purposes of a tty
                          session, has been terminated."
                        --#TYPE "Telnet session terminated"
                        --#SUMMARY "Session type %d closed"
                        --#ARGUMENTS {0}
                        --#SEVERITY MINOR
                        --#TIMEINDEX 0
                        --#STATE OPERATIONAL

              ::= 1
END
