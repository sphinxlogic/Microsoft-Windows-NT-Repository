XYPLEX-ETHERNET-MIB DEFINITIONS ::= BEGIN
            
                    IMPORTS
                            enterprises, Counter
                                    FROM RFC1155-SMI
                            OBJECT-TYPE
                                    FROM RFC1212-CONCISE-MIB;
            
            xyplex          OBJECT IDENTIFIER ::= { enterprises 33 }
            ethernet        OBJECT IDENTIFIER ::= { xyplex 11 }
            
            --  This MIB module uses the extended OBJECT-TYPE macro as
            --  defined in [9]
            
            --  this is the MIB module for Xyplex Ethernet interfaces





























            
            

            
            
            
            
            -- the Generic Ethernet group
            
            -- Implementation of this group is mandatory for all Xyplex
            -- systems that have an Ethernet interface
            
            etherTable OBJECT-TYPE
                SYNTAX SEQUENCE OF EtherEntry
                ACCESS not-accessible
                STATUS mandatory
                DESCRIPTION
                    "A list of generic entries."
                ::= { ethernet 1 }
            
            etherEntry OBJECT-TYPE
                SYNTAX EtherEntry
                ACCESS not-accessible
                STATUS mandatory
                DESCRIPTION
                    "Generic status and parameter values for an Ethernet 
                    interface."
                INDEX { etherIndex }
                ::= { etherTable 1 }
            
            EtherEntry ::=
                SEQUENCE {
                    etherIndex
                        INTEGER,
                    etherAlignmentErrors
                        Counter,
                    etherFCSErrors
                        Counter
                }
            
            etherIndex OBJECT-TYPE
                SYNTAX INTEGER
                ACCESS read-only
                STATUS mandatory
                DESCRIPTION
                    "An index value that uniquely identifies an Ethernet 
                    interface.  The interface identified by a particular 
                    value of this index is the same interface as 
                    identified by the same value of ifIndex."
                ::= { etherEntry 1 }
            
            etherAlignmentErrors OBJECT-TYPE
                SYNTAX Counter

            
            

            
            
            
            
                ACCESS read-only
                STATUS mandatory
                DESCRIPTION
                    "A count of frames received on a particular 
                    interface that are not an integral number of octets 
                    in length and do not pass the FCS check."
                ::= { etherEntry 2 }
            
            etherFCSErrors OBJECT-TYPE
                SYNTAX Counter
                ACCESS read-only
                STATUS mandatory
                DESCRIPTION
                    "A count of frames received on a particular 
                    interface that are an integral number of octets in 
                    length that do not pass the FCS check."
                ::= { etherEntry 3 }





























            
            

            
            
            
            
            -- the Ethernet Transmit group
            
            -- Implementation of this group is mandatory for all Xyplex
            -- systems that transmit messages on an Ethernet interface
            
            etherTxTable OBJECT-TYPE
                SYNTAX SEQUENCE OF EtherTxEntry
                ACCESS not-accessible
                STATUS mandatory
                DESCRIPTION
                    "A list of Ethernet transmit entries."
                ::= { ethernet 2 }
            
            etherTxEntry OBJECT-TYPE
                SYNTAX EtherTxEntry
                ACCESS not-accessible
                STATUS mandatory
                DESCRIPTION
                    "Transmit status and parameter values for an 
                    Ethernet interface."
                INDEX { etherTxIndex }
                ::= { etherTxTable 1 }
            
            EtherTxEntry ::=
                SEQUENCE {
                    etherTxIndex
                        INTEGER,
                    etherTxSingleCollisionFrames
                        Counter,
                    etherTxMultipleCollisionFrames
                        Counter
                }
            
            etherTxIndex OBJECT-TYPE
                SYNTAX INTEGER
                ACCESS read-only
                STATUS mandatory
                DESCRIPTION
                    "An index value that uniquely identifies an Ethernet 
                    interface.  The interface identified by a particular 
                    value of this index is the same interface as 
                    identified by the same value of ifIndex."
                ::= { etherTxEntry 1 }
            
            etherTxSingleCollisionFrames OBJECT-TYPE
                SYNTAX Counter

            
            

            
            
            
            
                ACCESS read-only
                STATUS mandatory
                DESCRIPTION
                    "A count of successfully transmitted frames on a 
                    particular interface for which transmission is 
                    inhibited by exactly one collision.  A frame that is 
                    counted by an instance of this object is also 
                    counted by the corresponding instance of either the 
                    ifOutUcastPkts or ifOutNUcastPkts object and is not 
                    counted by the corresponding instance of the 
                    etherTxMultipleCollisionFrames object."
                ::= { etherTxEntry 2 }
            
            etherTxMultipleCollisionFrames OBJECT-TYPE
                SYNTAX Counter
                ACCESS read-only
                STATUS mandatory
                DESCRIPTION
                    "A count of successfully transmitted frames on a 
                    particular interface for which transmission is 
                    inhibited by more than one collision.  A frame that 
                    is counted by an instance of this object is also 
                    counted by the corresponding instance of either the 
                    ifOutUcastPkts or ifOutNUcastPkts object and is not 
                    counted by the corresponding instance of the 
                    etherTxSingleCollisionFrames object."
                ::= { etherTxEntry 3 }



















            
            

            
            
            
            
            -- the Ethernet Multicast group
            
            -- Implementation of this group is optional;  it is
            -- appropriate for all Xyplex systems on which the
            -- necessary monitoring is feasible
            
            etherMulticastTable OBJECT-TYPE
                SYNTAX SEQUENCE OF EtherMulticastEntry
                ACCESS not-accessible
                STATUS mandatory
                DESCRIPTION
                    "A list of etherMulticast entries."
                ::= { ethernet 3 }
            
            etherMulticastEntry OBJECT-TYPE
                SYNTAX EtherMulticastEntry
                ACCESS not-accessible
                STATUS mandatory
                DESCRIPTION
                    "EtherMulticast status and parameter values for an 
                    Ethernet interface."
                INDEX { etherMulticastIndex }
                ::= { etherMulticastTable 1 }
            
            EtherMulticastEntry ::=
                SEQUENCE {
                    etherMulticastIndex
                        INTEGER,
                    etherMulticastBytesIn
                        Counter,
                    etherMulticastBytesOut
                        Counter
                }
            
            etherMulticastIndex OBJECT-TYPE
                SYNTAX INTEGER
                ACCESS read-only
                STATUS mandatory
                DESCRIPTION
                    "An index value that uniquely identifies an Ethernet 
                    interface.  The interface identified by a particular 
                    value of this index is the same interface as 
                    identified by the same value of ifIndex."
                ::= { etherMulticastEntry 1 }
            
            etherMulticastBytesIn OBJECT-TYPE

            
            

            
            
            
            
                SYNTAX Counter
                ACCESS read-only
                STATUS mandatory
                DESCRIPTION
                    "A count of frames successfully received on a 
                    particular interface and for which the destination 
                    address multicast bit was set.  Bytes that are 
                    counted by an instance of this object are also 
                    counted by the corresponding instance of the 
                    ifInOctets object."
                ::= { etherMulticastEntry 2 }
            
            etherMulticastBytesOut OBJECT-TYPE
                SYNTAX Counter
                ACCESS read-only
                STATUS mandatory
                DESCRIPTION
                    "A count of successfully frames successfully 
                    transmitted on a particular interface and for which 
                    the destination address multicast bit was set.  
                    Bytes that are counted by an instance of this object 
                    are also counted by the corresponding instance of 
                    the ifOutOctets object."
                ::= { etherMulticastEntry 3 }






















            
            

            
            
            
            
            -- the Ethernet Extended Transmit group
            
            -- Implementation of this group is optional;  it is
            -- appropriate for all Xyplex systems on which the
            -- necessary monitoring is feasible
            
            etherXTxTable OBJECT-TYPE
                SYNTAX SEQUENCE OF EtherXTxEntry
                ACCESS not-accessible
                STATUS mandatory
                DESCRIPTION
                    "A list of Ethernet extended transmit entries."
                ::= { ethernet 4 }
            
            etherXTxEntry OBJECT-TYPE
                SYNTAX EtherXTxEntry
                ACCESS not-accessible
                STATUS mandatory
                DESCRIPTION
                    "Extended transmit status and parameter values for 
                    an Ethernet interface."
                INDEX { etherXTxIndex }
                ::= { etherXTxTable 1 }
            
            EtherXTxEntry ::=
                SEQUENCE {
                    etherXTxIndex
                        INTEGER,
                    etherXTxExcessiveCollisions
                        Counter
                }
            
            etherXTxIndex OBJECT-TYPE
                SYNTAX INTEGER
                ACCESS read-only
                STATUS mandatory
                DESCRIPTION
                    "An index value that uniquely identifies an Ethernet 
                    interface.  The interface identified by a particular 
                    value of this index is the same interface as 
                    identified by the same value of ifIndex."
                ::= { etherXTxEntry 1 }
            
            etherXTxExcessiveCollisions OBJECT-TYPE
                SYNTAX Counter
                ACCESS read-only

            
            

            
            
            
            
                STATUS mandatory
                DESCRIPTION
                    "A count of frames for which transmission on a 
                    particular interface fails due to excessive 
                    collisions."
                ::= { etherXTxEntry 2 }
            
END
