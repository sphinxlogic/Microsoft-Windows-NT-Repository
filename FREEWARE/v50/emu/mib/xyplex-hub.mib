XYPLEX-HUB-MIB DEFINITIONS ::= BEGIN
            
                    IMPORTS
                            enterprises, Counter
                                    FROM RFC1155-SMI
                            DisplayString
                                    FROM RFC1158-MIB
                            OBJECT-TYPE
                                    FROM RFC1212-CONCISE-MIB
                            DateTime
                                    FROM XYPLEX-SYSTEM-MIB;
            
            xyplex          OBJECT IDENTIFIER ::= { enterprises 33 }
            hub             OBJECT IDENTIFIER ::= { xyplex 9 }
            
            --  This MIB module uses the extended OBJECT-TYPE macro as
            --  defined in [9]
            
            --  this is the MIB module for Xyplex Ethernet hubs

























            
            

            
            
            
            
            -- the Hub group
            
            -- Implementation of this group is mandatory for all Xyplex
            -- Ethernet hubs that support SNMP management
            
            hubTwistedPairPortNumber OBJECT-TYPE
                SYNTAX INTEGER
                ACCESS read-only
                STATUS mandatory
                DESCRIPTION
                    "The number of twisted-pair hub ports.  By 
                    convention, these are the lower numbered hub ports.  
                    Corresponds indirectly to the numbered, twisted-pair 
                    port numbers labeled 'Port' in the SHOW HUB SUMMARY 
                    display."
            ::= { hub 1 }
            
            hubNonTwistedPairPortNumber OBJECT-TYPE
                SYNTAX INTEGER
                ACCESS read-only
                STATUS mandatory
                DESCRIPTION
                    "The number of non-twisted-pair hub ports.  By 
                    convention, these are the higher numbered hub ports.  
                    Corresponds indirectly to the unnumbered, 
                    non-twisted-pair ports in the SHOW HUB SUMMARY 
                    display."
            ::= { hub 2 }


















            
            

            
            
            
            
            -- the Hub Port table
            
            hubPortTable OBJECT-TYPE
                SYNTAX SEQUENCE OF HubPortEntry
                ACCESS not-accessible
                STATUS mandatory
                DESCRIPTION
                    "A list of hub Ethernet port entries."
                ::= { hub 3 }
            
            hubPortEntry OBJECT-TYPE
                SYNTAX HubPortEntry
                ACCESS not-accessible
                STATUS mandatory
                DESCRIPTION
                    "Hub parameter values for an Ethernet port."
                INDEX { hubPortIndex }
                ::= { hubPortTable 1 }
            
            HubPortEntry ::=
                SEQUENCE {
                    hubPortIndex
                        INTEGER,
                    hubPortName
                        DisplayString,
                    hubPortAutoPolarity
                        INTEGER,
                    hubPortSensedPolarity
                        INTEGER,
                    hubPortPulse
                        INTEGER,
                    hubPortPulseStatus
                        INTEGER,
                    hubPortMissedPulses
                        COUNTER,
                    hubPortJabbers
                        COUNTER,
                    hubPortBadPreambles
                        COUNTER,
                    hubPortBitRateErrors
                        COUNTER,
                    hubPortLateCollisions
                        COUNTER,
                    hubPortNormalCollisions
                        COUNTER,
                    hubPortZero

            
            

            
            
            
            
                        INTEGER,
                    hubPortZeroTime
                        TimeTicks
                }
            
            hubPortIndex OBJECT-TYPE
                SYNTAX INTEGER
                ACCESS read-only
                STATUS mandatory
                DESCRIPTION
                    "An index value that uniquely identifies a port.  
                    The port identified by a particular value of this 
                    index is the same port as identified by portBasicID 
                    in hmBasicPortTable in the IEEE Hub MIB [11].  
                    Corresponds directly to the numbered, twisted-pair 
                    port numbers labeled 'port' and indirectly to the 
                    unnumbered, non-twisted-pair ports in the SHOW HUB 
                    SUMMARY display."
                ::= { hubPortEntry 1 }
            
            hubPortName OBJECT-TYPE
                SYNTAX DisplayString (SIZE (0..16))
                ACCESS read-write
                STATUS mandatory
                DESCRIPTION
                    "An administratively assigned name for a 
                    twisted-pair port, typically with some local 
                    significance.  Corresponds directly to PORT NAME and 
                    the value labeled 'Name' in the SHOW HUB SUMMARY 
                    display."
                ::= { hubPortEntry 2 }
            
            hubPortAutoPolarity OBJECT-TYPE
                SYNTAX INTEGER { disabled(1), enabled(2) }
                ACCESS read-write
                STATUS mandatory
                DESCRIPTION
                    "A control for automatic determination of 
                    twisted-pair port polarity.  'disabled' locks the 
                    port into positive polarity.  'enabled' allows the 
                    hub to sense polarity and adapt accordingly.  
                    Corresponds directly to PORT POLARITY and the value 
                    labeled 'Auto Polarity:' in the PORT display."
                ::= { hubPortEntry 3 }
            
            hubPortSensedPolarity OBJECT-TYPE

            
            

            
            
            
            
                SYNTAX INTEGER { reversed(1), normal(2) }
                ACCESS read-only
                STATUS mandatory
                DESCRIPTION
                    "Polarity of a twisted-pair port.  Corresponds 
                    directly to PORT POLARITY and the value labeled 
                    'Polarity:' in the HUB SUMMARY display."
                ::= { hubPortEntry 4 }
            
            hubPortPulse OBJECT-TYPE
                SYNTAX INTEGER { disabled(1), enabled(2) }
                ACCESS read-write
                STATUS mandatory
                DESCRIPTION
                    "A control for periodic, automatic generation of a 
                    test pulse on a twisted-pair port.  Corresponds 
                    directly to PORT TEST PULSE and the value labeled 
                    'Test Pulse:' in the PORT display."
                ::= { hubPortEntry 5 }
            
            hubPortPulseStatus OBJECT-TYPE
                SYNTAX INTEGER { missed(1), detected(2) }
                ACCESS read-only
                STATUS mandatory
                DESCRIPTION
                    "Status of the last attempt to generate and detect a 
                    test pulse.  Corresponds directly to the value 
                    labeled 'STATUS' and 'Test Pulse:' in the PORT 
                    display."
                ::= { hubPortEntry 6 }
            
            hubPortMissedPulses OBJECT-TYPE
                SYNTAX Counter
                ACCESS read-only
                STATUS mandatory
                DESCRIPTION
                    "Number of times that a generated test pulse was not 
                    seen in return.  Corresponds directly to the value 
                    labeled 'Test Pulse Lost:' in the PORT display."
                ::= { hubPortEntry 7 }
            
            hubPortJabbers OBJECT-TYPE
                SYNTAX Counter
                ACCESS read-only
                STATUS mandatory
                DESCRIPTION

            
            

            
            
            
            
                    "Number of times that a received frame was 
                    terminated by the jabber timer.  Corresponds 
                    directly to the value labeled 'Jabbers:' in the PORT 
                    display."
                ::= { hubPortEntry 8 }
            
            hubPortBadPreambles OBJECT-TYPE
                SYNTAX Counter
                ACCESS read-only
                STATUS mandatory
                DESCRIPTION
                    "Number of times that two one bits (Start of Frame) 
                    did not follow an interpacket gap and alternating 
                    one and zero bits.  Corresponds directly to the 
                    value labeled 'SOF Missing:' in the PORT display."
                ::= { hubPortEntry 9 }
            
            hubPortBitRateErrors OBJECT-TYPE
                SYNTAX Counter
                ACCESS read-only
                STATUS mandatory
                DESCRIPTION
                    "Number of times that bits were received with 
                    improper timing.  Corresponds directly to the value 
                    labeled 'Out of Spec. Bit Rate:' in the PORT 
                    display."
                ::= { hubPortEntry 10 }
            
            hubPortLateCollisions OBJECT-TYPE
                SYNTAX Counter
                ACCESS read-only
                STATUS mandatory
                DESCRIPTION
                    "Number of times that a frame collision came after 
                    the allowed collision window.  Corresponds directly 
                    to the value labeled 'Late Collisions:' in the PORT 
                    display."
                ::= { hubPortEntry 11 }
            
            hubPortNormalCollisions OBJECT-TYPE
                SYNTAX Counter
                ACCESS read-only
                STATUS mandatory
                DESCRIPTION
                    "Number of times that a frame collision came within 
                    the allowed collision window.  Corresponds directly 

            
            

            
            
            
            
                            to the value labeled 'Collisions:' in the PORT 
                    display."
                ::= { hubPortEntry 12 }
            
            hubPortZero OBJECT-TYPE
                SYNTAX INTEGER { ready(1), execute(2) }
                ACCESS read-write
                STATUS mandatory
                DESCRIPTION
                    "Control to zero counters kept for the port.  In 
                    response to a get-request or get-next-request, the 
                    agent always returns 'ready' for this value.  
                    Setting the value to 'ready' has no effect.  Setting 
                    it to 'execute' causes all the system's counters to 
                    be zeroed.  Corresponds to the ZERO PORT command."
                ::= { hubPortEntry 13 }
            
            hubPortZeroTime OBJECT-TYPE
                SYNTAX TimeTicks
                ACCESS read-only
                STATUS mandatory
                DESCRIPTION
                    "The number of hundredths of a second since the most 
                    recent zeroing of the counters kept for the port, 
                    such as through execution of sysZeroAll or 
                    hubPortZero.  Corresponds directly to the value 
                    labeled 'Since Zeroed:' in the PORT COUNTERS 
                    display."
                ::= { hubPortEntry 14 }
            
END
