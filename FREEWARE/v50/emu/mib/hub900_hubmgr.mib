DECHUB900-HUBMGR-MIB DEFINITIONS ::= BEGIN

--
--
--  Definitions of Managed Objects for Digital Equipment Corporation's
--              DEChub900 MultiSwitch Hub Management Module
--              ===========================================
--
--
--
--                 Name:    dechub900-hubmgr-mib-v1-1.txt
--                 Version: 1.1
--                 Date:    May, 1994
--                 Company: Digital Equipment Corporation
--                 Mail:    hub900-support@lkg.dec.com
--
--  
--  
--  
--  This Digital Equipment  Corporation  SNMP  Management  Information  Base
--  Specification  embodies Digital Equipment Corporation's confidential and
--  proprietary  intellectual  property.   Digital   Equipment   Corporation
--  retains  all  title  and  ownership  in the Specification, including any
--  revisions.
--  
--  It is Digital Equipment Corporation's intent to encourage the widespread
--  use  of  this Specification in connection with the management of Digital
--  Equipment Corporation products.
--  
--  Digital Equipment  Corporation  grants  vendors,  end-users,  and  other
--  interested  parties a non-exclusive license to use this Specification in
--  connection  with  the  management  of  Digital   Equipment   Corporation
--  products.
--  
--  Digital Equipment Corporation reserves the right to make changes in this
--  specification  and  other information contained in this document without
--  prior notice.
--  
--  Digital Equipment Corporation makes no  warranty,  either  expressed  or
--  implied,  as  to  the  use,  operation, condition, or performance of the
--  Specification.  In no  event  shall  Digital  Equipment  Corporation  be
--  liable  for  any incidental, indirect, special, or consequential damages
--  whatsoever (including but not limited to loss of profits) arising out of
--  or related to this document or the information contained in it.
--  
--
--
--
--
--
--  1  Status Of This Memo
--
--  This  MIB  module  provides  definitions  for   Digital   Equipment
--  Corporation's DEChub900 MultiSwitch Hub Management Module.
--
--  Digital offers Internet anonymous ftp access to DEChub900 MIBs from 
--  gatekeeper.dec.com.
--
--      1)  User the Internet application "ftp" to connect to 
--          gatekeeper.dec.com (Internet address 16.1.0.2).
--      2)  Log in as user "anonymous".
--      3)  Use you electronic mail address as the password.
--      4)  Change directories to the /pub/DEC/hub900/mibs area using
--          "cd /pub/DEC/hub900/mibs".
--      5)  Use the "ascii" command to specify that you are 
--          retrieving ASCII test files.
--      6)  Get the README file using "get README".
--      7)  The README file explains how to retrieve this MIB.
--          It lists the latest version on the MIB.  It may
--          instruct you to "cd" to another directory where
--          you can "get" this MIB.
--      8)  When you are finished, use the "quit" command to log out.
--
--  Inquiries about the contents and use of this MIB may be sent to 
--  hub900-support@lkg.dec.com.
--
--
--  2  Relationship To Other MIBs
--
--  The  objects  defined  in  this   MIB   are   located   under   the
--  private.enterprises subtree as shown below:
--
--                    iso(1).org(3).dod(6).internet(1)
--                                 |
--                              private(4)
--                                 |
--                              enterprises(1)
--                                 |
--                              dec(36)
--                                 |
--                              ema(2)
--                                 |
--                              decMIBextension(18)
--                                 |
--                              decHub900(11)
--                                 |
--                     .___________.___________.___________// ...etc...
--                     |                       |
--                mgmtAgent(1)              common(2)
--                     |                       |    
--                mgmtAgentVersion1(1)      ...ect...
--                     |
--       ._____________._____________._____________.
--       |             |             |             |
--       |             |        .________________________________.
--   chassis(1)     hrip(2)     |  hubIp(3)     hubAuthCreate(4) |
--                              |________________________________|
--
--  This MIB contains  definitions  for  the  hubIp  and  hubAuthCreate
--  groups.
--
--
--
--  3  Abstract
--
--  This MIB is implemented by the DEChub900 MultiSwitch Hub Management
--  Module.   The Hub Manager is a microprocessor-based controller used
--  to monitor, configure, and control the DEChub900.
--
--  The Hub Manager implements RFC 1213 (MIB-II) and other  MIBs  which
--  are  defined  under  the  private.enterprises.dec  subtree  of  the
--  internet subtree as defined in RFC 1155 (SMI).
--
--  Use of the objects defined in this MIB is described in the  "DEChub
--  900 MultiSwitch Owner's Manual".  Where discrepancies occur between
--  this MIB document and the owner's manual the owner's  manual  takes
--  precedence.
--
--  Two groups of objects are defined within  this  MIB:   the  Hub  IP
--  Forwarding and Hub Authentication Creation groups.
--
--
--
--  4  The Hub IP Forwarding Group
--
--  The Hub Manager contains an out-of-band management (OBM) port and a
--  console  port.  The OBM port allows management over the Serial Line
--  Internet Protocol (SLIP) using a modem or direct connection to  the
--  OBM port.
--
--  The  Hub  Manager  does  not  have  an   in-band   connection   for
--  communicating  with  network management stations.  A network module
--  that supports IP Services, such as the DECrepeater  900TM,  can  be
--  used to provide an in-band connection for the Hub Manager.
--
--  The Hub IP Forwarding Group  is  used  to  set  up  an  IP  Service
--  connection of the Hub Manager and IP server module.
--
--  For example, a DECrepeater 900 installed in slot 4 of the DEChub900
--  chassis  can  be  configured to provide an in-band connection using
--  the hubIpServerTable.
--    
--                                Hub Manager
--                                    |
--                                    |
--                           backplane interfaces
--            .______.______.______.______.______.______.______.
--            |      |      |      |      |      |      |      |
--          .___.  .___.  .___.  .___.  .___.  .___.  .___.  .___.  
--          |   |  |   |  |   |  |   |  |   |  |   |  |   |  |   | 
--          | s |  | s |  | s |  | s |  | s |  | s |  | s |  | s |
--          | l |  | l |  | l |  | l |  | l |  | l |  | l |  | l |
--          | o |  | o |  | o |  | o |  | o |  | o |  | o |  | o |
--          | t |  | t |  | t |  | t |  | t |  | t |  | t |  | t |
--          | - |  | - |  | - |  | - |  | - |  | - |  | - |  | - |
--          | 1 |  | 2 |  | 3 |  | 4 |  | 5 |  | 6 |  | 7 |  | 8 |
--          |   |  |   |  |   |  |   |  |   |  |   |  |   |  |   |
--          |___|  |___|  |___|  |___|  |___|  |___|  |___|  |___|  
--                                 |
--                                 |    In-band connection
--                                 =============================>>
--
--  First, the  in-band  IP  address  must  be  configured  by  setting
--  hubIpServerAddr.4  (for  the  module  in  slot 4) to the desired IP
--  address.  Next, hubIpServerAdminStatus must be set  to  adminUp(1).
--  hubIpServerOperStatus  reflects  the  status  of the operation.  If
--  hubIpServerOperStatus is operUp(1) then  the  connection  has  been
--  successfully  established.  If hubIpServerOperStatus is operDown(2)
--  then the connection was not established.  The connection might  not
--  be  established of the module is slot for is incapable of providing
--  the  services.   For  example,  the  DECrepeater   900   might   be
--  partitioned.  Consult the DEChub 900 MultiSwitch Owner's Manual for
--  troubleshooting procedures.
--
--
--
--  5  The HubAuthCreate Group
--
--  An entry is created using the main agents values, along with a  set
--  of  'create  flags'  which  are user selectable (they're read-write
--  objects).   The  OneHub  Authentication   Database   augments   the
--  traditional database with the following 'create flags':
--
--     Object                       Values                   Default
--     ____________________________ ________________________ ____________
--     authCreateTrapCommunity      default(1), inherit(2)   inherit(2)
--     authCreateTrapUsers          default(1), inherit(2)   inherit(2)
--     authCreateReadOnlyCommunity  default(1), inherit(2)   inherit(2)
--     authCreateReadOnlyUsers      default(1), inherit(2)   inherit(2)
--     authCreateReadWriteCommunity default(1), inherit(2)   inherit(2)
--     authCreateReadWriteUsers     default(1), inherit(2)   inherit(2)
--     ____________________________ ________________________ ____________
--
--  Two examples  are  shown;  one  uses  'defaults',  the  other  uses
--  'inheritance'.    (It's  left  as  an  exercise  to  the  reader to
--  extrapolate the two other combinations. ;-)
--
--
--
--
--  5.1  Example 1 - Create With Defaults. -
--
--  In this example, both create flags indicate that the authentication
--  database entry should be created using defaults.  The newly created
--  entry (slot 2) does not inherit anything from the main agent  (slot
--  0).
--
--
--
--    createReadOnlyCom    = SNMP_K_CREATE_DEFAULTS
--    createReadOnlyUsers  = SNMP_K_CREATE_DEFAULTS
--    createReadWriteCom   = SNMP_K_CREATE_DEFAULTS
--    createReadWriteUsers = SNMP_K_CREATE_DEFAULTS
--
--
--    Slot  Entity Description   EntityIPAddress  Community    Rights
--    ____  ____________________ _______________  ____________ ______
--     0    Hub Manager          16.21.16.128     public       read-only
--     0    Hub Manager          16.21.16.128     private      read-write
--     2    Ethernet Repeater    16.21.16.128     public-2     read-only
--     2    Ethernet Repeater    16.21.16.128     public-2     read-write
--
--
--  As shown, when  created  by  default,  the  community  is  "public"
--  concatenated  with  a dash, followed by the extended slot number of
--  the hub module.  The user list is  initially  empty,  allowing  any
--  user  access  to  the  community.  (Because createReadOnlyUsers and
--  createReadWriteUsers are both  set  to  SNMP_K_CREATE_DEFAULTS  the
--  default user list which allows any module access is created.)
--
--  If the module has its own IP address  and  SNMP  agent,  the  newly
--  created  entry  might  have two additional entries in the table, as
--  follows:
--
--
--    Slot  Entity Description   EntityIPAddress  Community    Rights
--    ____  ____________________ _______________  ____________ ______
--     0    Hub Manager          16.21.16.128     public       read-only
--     0    Hub Manager          16.21.16.128     private      read-write
--     2    Ethernet Repeater    16.21.16.128     public-2     read-only
--     2    Ethernet Repeater    16.21.16.128     public-2     read-write
--     2    Ethernet Repeater    16.20.10.40      public       read-only
--     2    Ethernet Repeater    16.20.10.40      private      read-write
--
--
--  The last two entries in the table refer  to  the  module's  own  IP
--  address.   The  module  reports  these  entries to the Hub Manager.
--  Since they refer to the modules own IP address, they are completely
--  independent of the creation process.
--
--
--
--  5.2  Example 2 - Create By Inheritance -
--
--  In this example, both create flags indicate that the authentication
--  database  entry should be created by inheriting attributes from the
--  main  agent.   The  newly  created  entry  (slot  2)  inherits  the
--  community string prefix "private" and the entire user list from the
--  main agent.
--   
--
--    createReadOnlyCom    = SNMP_K_INHERIT_FROM_HUB
--    createReadOnlyUsers  = SNMP_K_INHERIT_FROM_HUB
--    createReadWriteCom   = SNMP_K_INHERIT_FROM_HUB
--    createReadWriteUsers = SNMP_K_INHERIT_FROM_HUB
--
--    Slot  Entity Description   EntityIPAddress  Community    Rights
--    ____  ____________________ _______________  ____________ ______
--     0    Hub Manager          16.21.16.128     public       read-only
--     0    Hub Manager          16.21.16.128     private      read-write
--     2    Ethernet Repeater    16.21.16.128     public-2     read-only
--     2    Ethernet Repeater    16.21.16.128     private-2    read-write
--
--
--  As shown, when created by  inheritance,  the  community  prefix  is
--  inherited  from  the  main agent.  A dash, followed by the extended
--  slot number of the hub module is concatenated to  the  prefix.   In
--  this  example,  the  user  list is inherited from the main agent as
--  well, because createReadOnlyUsers and createReadWriteUsers are both
--  set  to  SNMP_K_INHERIT_FROM_HUB.   If the Hub Manager allowed only
--  users at 16.21.16.121 and 16.21.*.* access, then the  newly  create
--  module will also only allow access to these users.
--
--  If the module has its own IP address  and  SNMP  agent,  the  newly
--  created  entry  might  have two additional entries in the table, as
--  follows:
--
--    Slot  Entity Description   EntityIPAddress  Community    Rights
--    ____  ____________________ _______________  ____________ ______
--     0    Hub Manager          16.21.16.128     public       read-only
--     0    Hub Manager          16.21.16.128     private      read-write
--     2    Ethernet Repeater    16.21.16.128     public-2     read-only
--     2    Ethernet Repeater    16.21.16.128     public-2     read-write
--     2    Ethernet Repeater    16.20.10.40      public       read-only
--     2    Ethernet Repeater    16.20.10.40      private      read-write
--
--  The last two entries in the table refer  to  the  module's  own  IP
--  address.   The  module  reports  these  entries to the Hub Manager.
--  Since they refer to the modules own IP address, they are completely
--  independent of the creation process.
--
--
--
--  6  References
--
--
--  [1]  RFC 1213.  McCloghrie, K., and M. Rose, "Management Information Base 
--       for Network Management of TCP/IP-based Internets".  March, 1991.
--
--  [2]  RFC 1155.  Rose, M., and K. McCloghrie, "Structure and Identification 
--       of Management Information for TCP/IP-based Internets".  May, 1990.
--
--  [3]  DEChub 900 MultiSwitch Owner's Manual.  Digital Equipment 
--       Corp.  Order number:  EK-DH2MS-OM.<version>.
--
--
--
--
--  7  Object Synopsis
--
--
--  Object Name                            ObjId          Non-Vol
--  ===================================    =============  =======
--  hubAuthCreate                          p.3              n/a
--    hubAuthCreateTrapCommunity           p.3.1.0           y
--    hubAuthCreateTrapUsers               p.3.2.0           y
--    hubAuthCreateReadOnlyCommunity       p.3.3.0           y
--    hubAuthCreateReadOnlyUsers           p.3.4.0           y
--    hubAuthCreateReadWriteCommunity      p.3.5.0           y
--    hubAuthCreateReadWriteUsers          p.3.6.0           y
--  hubIp                                  p.4              n/a
--    hubIpDefaultInterface                p.4.1.0           y
--    hubIpMAMAddr                         p.4.2.0           y
--    hubIpServerTable                     p.4.3            n/a
--      hubIpServerEntry                   p.4.3.1          n/a
--        hubIpServerSlot                  p.4.3.1.1.n       y
--        hubIpServerIfIndex               p.4.3.1.2.n       y
--        hubIpServerAddr                  p.4.3.1.3.n       y
--        hubIpServerOperStatus            p.4.3.1.4.n       y
--        hubIpServerAdminStatus           p.4.3.1.5.n       y
--
--  where p is:  iso(1).org(3).dod(6).internet(1).private(4)
--                   enterprises(1).dec(36).ema(2).decMIBextension(18)
--                   decHub900(11).mgmtAgent(1).mgmtAgentVersion1(1)
--
--  and n is the instance of the tabular object.
--

IMPORTS
    IpAddress, enterprises
        FROM RFC1155-SMI
    OBJECT-TYPE
        FROM RFC-1212;

dec                 OBJECT IDENTIFIER ::= { enterprises 36 }
ema                 OBJECT IDENTIFIER ::= { dec 2 }
decMIBextension     OBJECT IDENTIFIER ::= { ema 18 }
decHub900           OBJECT IDENTIFIER ::= { decMIBextension 11 }
mgmtAgent           OBJECT IDENTIFIER ::= { decHub900 1 }
mgmtAgentVersion1   OBJECT IDENTIFIER ::= { mgmtAgent 1 }

--
--  Hub IP Forwarding Group.
--

hubIp  OBJECT IDENTIFIER ::= { mgmtAgentVersion1 3 }

hubIpDefaultInterface OBJECT-TYPE
    SYNTAX  INTEGER {
                obmPort(1),  -- OBM port is the default interface.
                             --   This is the default.
                slot1(2),    -- slot 1 (i.e., the line card in slot 1) is
                             --   the default interface.
                slot2(3),    -- slot 2 (i.e., the line card in slot 2) is
                             --   the default interface.
                slot3(4),    -- slot 3 (i.e., the line card in slot 3) is
                             --   the default interface.
                slot4(5),    -- slot 4 (i.e., the line card in slot 4) is
                             --   the default interface.
                slot5(6),    -- slot 5 (i.e., the line card in slot 5) is
                             --   the default interface.
                slot6(7),    -- slot 6 (i.e., the line card in slot 6) is
                             --   the default interface.
                slot7(8),    -- slot 7 (i.e., the line card in slot 7) is
                             --   the default interface.
                slot8(9)     -- slot 8 (i.e., the line card in slot 8) is
                             --   the default interface.
                }
    ACCESS  read-only
    STATUS  mandatory
    DESCRIPTION
        "Indicates which interface is to be used to transmit
         a packet if the destination address is not in the
         HUB's NetToMediaTable.  IP address/interface entries
         are added to the NetToMediaTable when the HUB/MAM
         receives a packet (via the OBM port or a line card
         acting as a server) or when the HUB is configured as
         IP server (i.e., the line card is the client).

         If a slot is selected as the default interface and
         the associated line card is not present or can not
         be configured as an IP server, the outgoing packet will
         be discarded."
    ::= { hubIp 1 }

hubIpMAMAddr OBJECT-TYPE
    SYNTAX  IpAddress
    ACCESS  read-write
    STATUS  mandatory
    DESCRIPTION
        "The MAM accepts or rejects incoming IP messages based
         on the destination of the message.  It does not matter
         over what interface the packet arrived.  This object
         is used to add an address to the appropriate tables
         to allow packets with this destination address to be
         accepted.

         This object is typically associated with IP traffic
         over the OBM port. However, it does not matter how
         the packet got to the IPS/IP layer."
    ::= { hubIp 2 }

--
-- Server Table
--

hubIpServerTable OBJECT-TYPE
    SYNTAX  SEQUENCE OF HubIpServerEntry
    ACCESS  not-accessible
    STATUS  mandatory
    DESCRIPTION
        "This table allows the monitoring/control of IP
         Forwarding servers for the HUB."
    ::= { hubIp 3 }

hubIpServerEntry OBJECT-TYPE
    SYNTAX  HubIpServerEntry
    ACCESS  not-accessible
    STATUS  mandatory
    DESCRIPTION
        "An entry in the hubIpServerTable."
    INDEX  
        { hubIpServerSlot }
    ::= { hubIpServerTable 1 }

HubIpServerEntry ::=
    SEQUENCE {
        hubIpServerSlot
           INTEGER,
        hubIpServerIfIndex
           INTEGER,
        hubIpServerAddr
           IpAddress,
        hubIpServerOperStatus
           INTEGER,
        hubIpServerAdminStatus
           INTEGER
    }

hubIpServerSlot OBJECT-TYPE
    SYNTAX  INTEGER (1..8)
    ACCESS  read-only
    STATUS  mandatory
    DESCRIPTION
        "The slot number (1-8) of the line card to act(acting)
         as an IP forwarding server for the HUB.  If the line card
         spans more than one slot, the lowest numbered slot is used.

         This object does not have a default value."
    ::= { hubIpServerEntry 1 }

hubIpServerIfIndex OBJECT-TYPE
    SYNTAX  INTEGER (1..255)
    ACCESS  read-only
    STATUS  mandatory
    DESCRIPTION
        "The index into the ifTable for the associated
         interface.  The appropriate interface is selected based
         on the slot number (hubIpServerSlot).  This object is
         initialized when AdminStatus transitions from adminDown(2) to
         adminUp(1)."
    ::= { hubIpServerEntry 2 }

hubIpServerAddr OBJECT-TYPE
    SYNTAX  IpAddress
    ACCESS  read-write
    STATUS  mandatory
    DESCRIPTION
        "The IP address for which the server is serving.  If
         the server receives a packet with this destination
         address, the packet will be forwarded to the HUB/MAM.
         This object cannot be set to IP addresses 255.255.255.255
         or 0.0.0.0.

         This object can only be changed if the AdminStatus is operDown(2).

         This object can not be changed in the same PDU that changes the
         AdminStatus."
    ::= { hubIpServerEntry 3 }

hubIpServerOperStatus OBJECT-TYPE
    SYNTAX  INTEGER {
                operUp(1),         -- able to forward packets
                operDown(2),       -- disabled from forwarding packets
                operNotPresent(3), -- line card is not currently
                                   --   inserted in the HUB
                operError(4)       -- some sort of error has occurred 
                                   --   preventing normal operation
               }
    ACCESS  read-only
    STATUS  mandatory
    DESCRIPTION
        "The current state of the server.  If the entry is in
         the notpresent(3) state,  and AdminStatus is up(1) it
         will be automatically configured when the line card is
         inserted in the HUB."
    ::= { hubIpServerEntry 4 }

hubIpServerAdminStatus OBJECT-TYPE
    SYNTAX  INTEGER {
                adminUp(1),  -- configured to forward packets
                adminDown(2) -- disabled from forwarding packets
               }
    ACCESS  read-write
    STATUS  mandatory
    DESCRIPTION
        "The desired state of the server.  Going from a adminDown(2)
         state to the adminUp(1) state causes an entry in the ifTable
         to be created for the associated slot if there isn't
         one.  If an entry already already exists, no ifTable
         entry is created, the existing entry is updated to
         reflect the transition.

         Going from adminUp(1) to adminDown(2) causes the associated entry
         in the ifTable to be marked down(2).

         adminDown(2) is the default for this object.

         The AdminStatus and IpServerAddr cannot be changed within the
         same PDU."
    ::= { hubIpServerEntry 5 }

--  +
--  
--  Authentication Create Flags.
--
--  Object Name                            ObjId          Non-Vol
--  ===================================    =============  =======
--  hubAuthCreate                          n.1
--    hubAuthCreateTrapCommunity           n.1.1.0           y
--    hubAuthCreateTrapUsers               n.1.2.0           y
--    hubAuthCreateReadOnlyCommunity       n.1.3.0           y
--    hubAuthCreateReadOnlyUsers           n.1.4.0           y
--    hubAuthCreateReadWriteCommunity      n.1.5.0           y
--    hubAuthCreateReadWriteUsers          n.1.6.0           y

--
--  Create flags.
--

hubAuthCreate      OBJECT IDENTIFIER ::= { mgmtAgentVersion1 4 }

hubAuthCreateTrapCommunity OBJECT-TYPE
    SYNTAX  INTEGER {
                default(1),
                inherit(2)
                }
    ACCESS  read-write
    STATUS  mandatory
    DESCRIPTION
        "This object controls how new trap communities are created.
        When the value of this object is default(1), new communities
        will be assigned the string 'public-n', where n is the
        number of the slot or extended slot in which the module
        resides.  When the value of this object is inherit(2),
        new communities will be assigned a string which consists
        of the Hub Manager's community with a '-n' concatenated
        to it.  For example, if the Hub Manager's community is
        'secret' and the value of this object is inherit, new
        communities for a module in slot 4 will be created as
        'secret-4'.

        The default value of this object is 'inherit(2)'.  The
        value of this object non-volatile."
    ::= { hubAuthCreate 1 }

hubAuthCreateTrapUsers OBJECT-TYPE
    SYNTAX  INTEGER {
                default(1),
                inherit(2)
                }
    ACCESS  read-write
    STATUS  mandatory
    DESCRIPTION
        "This object controls how trap user lists are created.
        When the value of this object is default(1), the trap user 
        list is created empty.  When the value of this object 
        is inherit(2), new trap user list will be assigned a the
        same values as the trap users list of the Hub Manager.

        The default value of this object is 'inherit(2)'.  The
        value of this object non-volatile."
    ::= { hubAuthCreate 2 }

hubAuthCreateReadOnlyCommunity OBJECT-TYPE
    SYNTAX  INTEGER {
                default(1),
                inherit(2)
                }
    ACCESS  read-write
    STATUS  mandatory
    DESCRIPTION
        "This object controls how new read-only communities are created.
        When the value of this object is default(1), new communities
        will be assigned the string 'public-n', where n is the
        number of the slot or extended slot in which the module
        resides.  When the value of this object is inherit(2),
        new communities will be assigned a string which consists
        of the Hub Manager's community with a '-n' concatenated
        to it.  For example, if the Hub Manager's community is
        'secret' and the value of this object is inherit, new
        communities for a module in slot 4 will be created as
        'secret-4'.

        The default value of this object is 'inherit(2)'.  The
        value of this object non-volatile."
    ::= { hubAuthCreate 3 }

hubAuthCreateReadOnlyUsers OBJECT-TYPE
    SYNTAX  INTEGER {
                default(1),
                inherit(2)
                }
    ACCESS  read-write
    STATUS  mandatory
    DESCRIPTION
        "This object controls how read-only user lists are created.
        When the value of this object is default(1), the read-only 
        user list is created to allow open access.  When the value 
        of this object is inherit(2), new read-only user list will 
        be assigned a the same values as the read-only user list of 
        the Hub Manager.

        The default value of this object is 'inherit(2)'.  The
        value of this object non-volatile."
    ::= { hubAuthCreate 4 }

hubAuthCreateReadWriteCommunity OBJECT-TYPE
    SYNTAX  INTEGER {
                default(1),
                inherit(2)
                }
    ACCESS  read-write
    STATUS  mandatory
    DESCRIPTION
        "This object controls how new read-write communities are created.
        When the value of this object is default(1), new communities
        will be assigned the string 'public-n', where n is the
        number of the slot or extended slot in which the module
        resides.  When the value of this object is inherit(2),
        new communities will be assigned a string which consists
        of the Hub Manager's community with a '-n' concatenated
        to it.  For example, if the Hub Manager's community is
        'secret' and the value of this object is inherit, new
        communities for a module in slot 4 will be created as
        'secret-4'.

        The default value of this object is 'inherit(2)'.  The
        value of this object non-volatile."
    ::= { hubAuthCreate 5 }

hubAuthCreateReadWriteUsers OBJECT-TYPE
    SYNTAX  INTEGER {
                default(1),
                inherit(2)
                }
    ACCESS  read-write
    STATUS  mandatory
    DESCRIPTION
        "This object controls how read-write user lists are created.
        When the value of this object is default(1), the read-write 
        user list is created to allow open access.  When the value 
        of this object is inherit(2), new read-write user list will 
        be assigned a the same values as the read-write user list of 
        the Hub Manager.

        The default value of this object is 'inherit(2)'.  The
        value of this object non-volatile."
    ::= { hubAuthCreate 6 }

END
