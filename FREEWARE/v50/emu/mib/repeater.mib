-- MIB created 1/17/96 13:41:56, by
--   SMIC (the next generation) version 1.6.29, November 22, 1994.

CISCO-REPEATER-MIB DEFINITIONS ::= BEGIN

-- From file: "CISCO-REPEATER-MIB.my"

IMPORTS
    OBJECT-TYPE
            FROM RFC-1212
    TruthValue
            FROM SNMPv2-TC-v1
    ciscoMgmt
            FROM CISCO-SMI
    rptrPortIndex,
    rptrPortGroupIndex
            FROM SNMP-REPEATER-MIB;

ciscoRptrMIB OBJECT IDENTIFIER ::= { ciscoMgmt 22 }
-- MODULE-IDENTITY
--  LastUpdated
--    9503090000Z
--  OrgName
--    Cisco Systems, Inc.
--  ContactInfo
--           Cisco Systems
--     Customer Service
--    
--    Postal: 170 W Tasman Drive
--     San Jose, CA  95134
--     USA
--    
--       Tel: +1 800 553-NETS
--    
--    E-mail: cs-snmp@cisco.com
--  RevDate
--    9503090000Z
--  RevDescr
--    Correct the definition for ciscoRptrPortMDIStatus.
--  RevDate
--    9410260000Z
--  RevDescr
--    Initial version of this MIB module.

ciscoRptrMIBObjects OBJECT IDENTIFIER ::= { ciscoRptrMIB 1 }
ciscoRptrMIBConformance OBJECT IDENTIFIER ::= { ciscoRptrMIB 2 }
ciscoRptrMIBCompliances OBJECT IDENTIFIER ::= { ciscoRptrMIBConformance 1 }
ciscoRptrMIBGroups OBJECT IDENTIFIER ::= { ciscoRptrMIBConformance 2 }

ciscoRptrPortTable OBJECT-TYPE
    SYNTAX SEQUENCE OF CiscoRptrPortEntry
    ACCESS not-accessible
    STATUS mandatory
    DESCRIPTION
        "Table of descriptive and status information about
                       the ports."
    ::= { ciscoRptrMIBObjects 1 }

ciscoRptrPortEntry OBJECT-TYPE
    SYNTAX CiscoRptrPortEntry
    ACCESS not-accessible
    STATUS mandatory
    DESCRIPTION
        "An entry in the table, containing information
                       about a single port."
    INDEX { rptrPortGroupIndex, rptrPortIndex }
-- Augments rptrPortEntry FROM SNMP-REPEATER-MIB
    ::= { ciscoRptrPortTable 1 }

CiscoRptrPortEntry ::= SEQUENCE {
    ciscoRptrPortMDIStatus INTEGER,
    ciscoRptrPortLinkTestEnabled TruthValue,
    ciscoRptrPortLinkTestFailed TruthValue,
    ciscoRptrPortAutoPolarityEnabled TruthValue,
    ciscoRptrPortAutoPolarityCorrected TruthValue,
    ciscoRptrPortSrcAddrCtrl TruthValue,
    ciscoRptrPortAllowedSrcAddr OCTET STRING,
    ciscoRptrPortAllowedSrcAddrStatus INTEGER,
    ciscoRptrPortLastIllegalSrcAddr OCTET STRING
    }

ciscoRptrPortMDIStatus OBJECT-TYPE
    SYNTAX INTEGER {
        normal(1),
        crossover(2),
        notSwitchable(3)
        }
    ACCESS read-only
    STATUS mandatory
    DESCRIPTION
        "This object indicates the port's MDI/MDI-X switching status.  
         The normal(1) status indicates the port is configured to be 
         standard MDI as defined by the 10BaseT Standard for hub port
         (allowing for connection to a chained hub).  The crossover(2) 
         status indicates the port is configured to be in MDI-X mode
         (allowing for connection to a 10BaseT end node).  The 
         notSwitchable(3) status indicates the port is not switchable 
         between MDI and MDI-X mode."
    ::= { ciscoRptrPortEntry 1 }

ciscoRptrPortLinkTestEnabled OBJECT-TYPE
    SYNTAX TruthValue
--    Rsyntax INTEGER {
--        true(1),
--        false(2)
--        }
    ACCESS read-write
    STATUS mandatory
    DESCRIPTION
        "Specifies whether or not Link Integrity Test Function is
         enabled for the port as specified by the 10BaseT Standard.  
         When the link test function is enabled, the absence of the 
         Link Test pulses and receive data on the port will cause the 
         port to go into a Link Fail state.  In this state, the data 
         transmission, data reception and collision detection functions
         are disabled until valid data or 4 consecutive Link Test 
         pulses appear on RXD+/- pair of the port.
        
         With the Link Integrity Test Function disabled, the data 
         driver, receiver and collision detection remain enabled 
         irrespective of the presence or absence of data or Link Test 
         pulses on the port."
    DEFVAL { true }
    ::= { ciscoRptrPortEntry 2 }

ciscoRptrPortLinkTestFailed OBJECT-TYPE
    SYNTAX TruthValue
--    Rsyntax INTEGER {
--        true(1),
--        false(2)
--        }
    ACCESS read-only
    STATUS mandatory
    DESCRIPTION
        "This object indicates the status of the Link Test function
         for the port.  Set to false indicates valid data or 4 
         consecutive Link Test pulses have been detected on the
         port.  Set to true indicates the failure of the Link Test 
         function for the port.  In the Link Test Fail state, data 
         transmission, data reception and collision detection functions
         are disabled until valid data or 4 consecutive Link Test pulses
         appear on the RXD+/- pair of the port."
    ::= { ciscoRptrPortEntry 3 }

ciscoRptrPortAutoPolarityEnabled OBJECT-TYPE
    SYNTAX TruthValue
--    Rsyntax INTEGER {
--        true(1),
--        false(2)
--        }
    ACCESS read-write
    STATUS mandatory
    DESCRIPTION
        "Specifies whether or not the Automatic Receiver Polarity 
         Reversal is enabled for the port.  This feature provides the 
         ability to invert the polarity of the signals appearing at the 
         RXD+/- pair of the port prior to re-transmission if the 
         polarity of the received signal is reversed (such as in the 
         case of wiring error)."
    DEFVAL { true }
    ::= { ciscoRptrPortEntry 4 }

ciscoRptrPortAutoPolarityCorrected OBJECT-TYPE
    SYNTAX TruthValue
--    Rsyntax INTEGER {
--        true(1),
--        false(2)
--        }
    ACCESS read-only
    STATUS mandatory
    DESCRIPTION
        "This object indicates the status of the Automatic Receiver
         Polarity Reversal for the port.  Set to true indicates the
         polarity of the port has been detected as reversed and is
         corrected.  Set to false indicates the polarity for the port
         as having correct polarity."
    ::= { ciscoRptrPortEntry 5 }

ciscoRptrPortSrcAddrCtrl OBJECT-TYPE
    SYNTAX TruthValue
--    Rsyntax INTEGER {
--        true(1),
--        false(2)
--        }
    ACCESS read-write
    STATUS mandatory
    DESCRIPTION
        "Specifies whether or not the Source Address Control feature is 
         enabled for the port.  This feature provides the ability to 
         control which device's specific MAC address is allowed access 
         to the network.  If the management entity specified an address
         via ciscoRptrPortAllowedSrcAddr, only the device with the 
         configured MAC address is allowed access to the network.  If 
         the management entity does not specified an address, the 
         allowed source address is learned from the last source address 
         if valid; otherwise, the allowed source address is learned from
         the MAC address of the first valid packet detected on the port.
         When another MAC address other than the allowed source address
         is detected on the port, the port is partitioned.
        
         WARNING: Configuring Source Address Control feature on the
         port which is used for management can cause the management
         entity to lose access to the agent if the management's source 
         address does not match the allowed source address."
    DEFVAL { false }
    ::= { ciscoRptrPortEntry 6 }

ciscoRptrPortAllowedSrcAddr OBJECT-TYPE
    SYNTAX OCTET STRING(SIZE(0 | 6))
    ACCESS read-write
    STATUS mandatory
    DESCRIPTION
        "For write access, this object is the allowed source address
         that is to be configured for source address control feature 
         for the port. 
        
         For read access, if no allowed source address was specifically 
         specified by the manager, the agent shall return the learned 
         address to control.  Otherwise, the specified allowed source 
         address is returned if configured by management entity."
    ::= { ciscoRptrPortEntry 7 }

ciscoRptrPortAllowedSrcAddrStatus OBJECT-TYPE
    SYNTAX INTEGER {
        allowedSrcAddrConfig(1),
        allowedSrcAddrLearn(2),
        allowedSrcAddrUndefined(3)
        }
    ACCESS read-only
    STATUS mandatory
    DESCRIPTION
        "This object indicates the status of ciscoRptrPortAllowedSrcAddr
         for the port.  allowedSrcAddrConfig(1) status indicates that 
         the allowed source address was explicitly configured by 
         management entity.  The allowedSrcAddrLearn(2) status indicates
         that the allowed source address was learned for the port.  
         The allowedSrcAddrUndefined(3) status indicates that currently
         there is no restriction on the source address for the port."
    ::= { ciscoRptrPortEntry 8 }

ciscoRptrPortLastIllegalSrcAddr OBJECT-TYPE
    SYNTAX OCTET STRING(SIZE(0 | 6))
    ACCESS read-only
    STATUS mandatory
    DESCRIPTION
        "This object is the last illegal source address which caused 
         this port to be partitioned.  If the port is never partitioned
         due to Source Address Control, the agent shall return a string
         of length zero."
    ::= { ciscoRptrPortEntry 9 }

ciscoRptrMIBGroup OBJECT IDENTIFIER ::= { ciscoRptrMIBGroups 1 }
-- OBJECT-GROUP
--  Status
--    mandatory
--  Descr
--    A collection of objects providing repeater ability.
--  objects
--    ciscoRptrPortMDIStatus, ciscoRptrPortLinkTestEnabled, 
--    ciscoRptrPortLinkTestFailed, ciscoRptrPortAutoPolarityEnabled, 
--    ciscoRptrPortAutoPolarityCorrected, ciscoRptrPortSrcAddrCtrl, 
--    ciscoRptrPortAllowedSrcAddr, 
--    ciscoRptrPortAllowedSrcAddrStatus, 
--    ciscoRptrPortLastIllegalSrcAddr

ciscoRptrMIBCompliance OBJECT IDENTIFIER ::= { ciscoRptrMIBCompliances 1 }
-- MODULE-COMPLIANCE
--  Status
--    mandatory
--  Descr
--    The compliance statement for entities which implement
--     the cisco Repeater MIB
--  Module
--    >>current<<
--   MandGroup
--    ciscoRptrMIBGroup


END
