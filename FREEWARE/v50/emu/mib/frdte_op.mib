-- Version 1.2.1.3, modified 3/24/94

          FRDTE-OPT-MIB DEFINITIONS ::= BEGIN

          IMPORTS
		  -- standard imports from SMI files

                  mgmt, NetworkAddress, IpAddress, Counter, Gauge,
                          TimeTicks
                      FROM RFC1155-SMI
                  OBJECT-TYPE
                          FROM RFC-1212

		  -- imports from cdx6500.smi specific to this module. Should
		  -- include Configuration, Statistics, and Control groups, as 
		  -- applicable. The two imports listed below are *examples*.

				  cdx6500Controls,
				  cdx6500PCTPortProtocolGroup,
				  cdx6500PSTPortProtocolGroup,
				  cdx6500PCTStationProtocolGroup,
				  cdx6500PSTStationProtocolGroup,
				  Counter16
				  FROM CDX6500-SMI;

          --  This MIB module uses the extended OBJECT-TYPE macro as
          --  defined in [14];


          -- textual conventions
		  -- These are "aliases" for commonly-used variants of the four primitive
		  -- object types provided by SNMP and also for user-defined object types.
		  -- Any definitions provided here are good only in this MIB, unless
		  -- explicitly listed as EXPORTs. DisplayString and PhysAddress are
		  -- commonly used textual conventions.

          DisplayString ::=
              OCTET STRING
          -- This data type is used to model textual information taken
          -- from the NVT ASCII character set.  By convention, objects
          -- with this syntax are declared as having
          --
          --      SIZE (0..255)

          PhysAddress ::=
              OCTET STRING
          -- This data type is used to model media addresses.  For many
          -- types of media, this will be in a binary representation.
          -- For example, an ethernet address would be represented as
          -- a string of 6 octets.


-- The Frame Relay DTE Port Configuration Table
-- This table contains Configuration paramaters 
-- for the Frame Relay DTE Port table.

cdx6500PCTFRDTEPortTable OBJECT-TYPE
	SYNTAX  SEQUENCE OF Cdx6500PCTFRDTEPortEntry
	ACCESS  not-accessible
	STATUS  mandatory
	DESCRIPTION
		"All of the configuration parameters relevant
		 to the Frame Relay DTE Port table."
	::= { cdx6500PCTPortProtocolGroup 5 }

cdx6500PCTFRDTEPortEntry OBJECT-TYPE
	SYNTAX  Cdx6500PCTFRDTEPortEntry
	ACCESS  not-accessible
	STATUS  mandatory
	DESCRIPTION
		"A row of SDLC Port configuration parameters."
	INDEX   { cdx6500frdtepCfgPortNum }
	::= { cdx6500PCTFRDTEPortTable 1 }

Cdx6500PCTFRDTEPortEntry ::=
	SEQUENCE {
		cdx6500frdtepCfgPortNum
			INTEGER,
                cdx6500frdtepConnectionType
                        INTEGER,
		cdx6500frdtepClockSource
			INTEGER,
		cdx6500frdtepClockSpeed
			INTEGER,
		cdx6500frdtepMaxStations
			INTEGER,
		cdx6500frdtepFrameSeqCounting
			INTEGER,
		cdx6500frdtepPktSeqCounting
			INTEGER,
		cdx6500frdtepCtrlProtocol
			INTEGER,
		cdx6500frdtepT391
			INTEGER,
		cdx6500frdtepT392
			INTEGER,
		cdx6500frdtepN391
			INTEGER,
		cdx6500frdtepN392
			INTEGER,
		cdx6500frdtepN393
			INTEGER,
		cdx6500frdtepNT1
			INTEGER,
		cdx6500frdtepNT2
			INTEGER,
		cdx6500frdtepNN1
			INTEGER,
		cdx6500frdtepNN2
			INTEGER,
		cdx6500frdtepNN3
			INTEGER
		}

cdx6500frdtepCfgPortNum OBJECT-TYPE
	SYNTAX  INTEGER (1..54)
    ACCESS  read-only
	STATUS  mandatory
	DESCRIPTION
		"Specifies the Port number for the Frame Relay Interface port you are
		selecting."
	::= { cdx6500PCTFRDTEPortEntry 1 }

cdx6500frdtepConnectionType OBJECT-TYPE
	SYNTAX		INTEGER {
				simp(0)
				}
	ACCESS		read-only
	STATUS		mandatory
	DESCRIPTION
		"Specify the control signal handshake and clocking required for a
		connection to be made to this port:

		simp  - simple, no control signals required"
	::= { cdx6500PCTFRDTEPortEntry 2 }

cdx6500frdtepClockSource OBJECT-TYPE
	SYNTAX		INTEGER	{
						int(0),
						ext(1)
						}
	ACCESS		read-only
	STATUS		mandatory
	DESCRIPTION
		"int - internal clock source
		ext - external clock source"
	::= { cdx6500PCTFRDTEPortEntry 3 }

cdx6500frdtepClockSpeed OBJECT-TYPE
	SYNTAX		INTEGER (1200..80000)
	ACCESS		read-only
	STATUS		mandatory
	DESCRIPTION
		"This is the speed of the port in bits per second, when using
		internal clocking.  The highest available speed is dependent on the
		card type, and on the interface type."
	::= { cdx6500PCTFRDTEPortEntry 4 }

cdx6500frdtepMaxStations OBJECT-TYPE
	SYNTAX		INTEGER
	ACCESS		read-only
	STATUS		mandatory
	DESCRIPTION
		"This is the highest station number to be configured on this FRI port.
		It is used to limit the configuration of stations."
	::= { cdx6500PCTFRDTEPortEntry 5 }

cdx6500frdtepFrameSeqCounting OBJECT-TYPE
	SYNTAX		INTEGER {
                                normal(0),
                                extended(1)
                                }
	ACCESS		read-only
	STATUS		mandatory
	DESCRIPTION
		"Port uses normal or extended frame sequence numbering:

		normal - normal sequencing  (modulo 8)
		ext  - extended sequencing (modulo 128)

		All stations on this port will be set to this value."
	::= { cdx6500PCTFRDTEPortEntry 6 }

cdx6500frdtepPktSeqCounting OBJECT-TYPE
	SYNTAX		INTEGER {
                                normal(0),
                                extended(1)
                                }
	ACCESS		read-only
	STATUS		mandatory
	DESCRIPTION
		"Port uses normal or extended packet level sequence numbers

		normal - normal sequencing (Modulo 8)
		ext  - extended sequencing (Modulo 128)

		This parameter must be set to the same value 
		at both this FRI port and the remote FRI port.
		All stations on this port will be set to this value."
	::= { cdx6500PCTFRDTEPortEntry 7 }

cdx6500frdtepCtrlProtocol OBJECT-TYPE
	SYNTAX		INTEGER {
                                annexD(0),
                                none(1),
                                lmi(2)
                                }
	ACCESS		read-only
	STATUS		mandatory
	DESCRIPTION
		"Whether ANSI T1.617 Annex D or LMI Support is enabled

		none    - None is enabled.
		annexD  - Annex D is enabled
		lmi     - LMI is enabled."

	::= { cdx6500PCTFRDTEPortEntry 8 }

cdx6500frdtepT391 OBJECT-TYPE
	SYNTAX		INTEGER
	ACCESS		read-only
	STATUS		mandatory
	DESCRIPTION
		"Link integrity verification timer.  FRI port sends status
		enquiry messages to network every T391 seconds."
	::= { cdx6500PCTFRDTEPortEntry 9 }

cdx6500frdtepT392 OBJECT-TYPE
	SYNTAX		INTEGER
	ACCESS		read-only
	STATUS		mandatory
	DESCRIPTION
		"Timer for verification of polling cycle.  FRI port expects status
		enquiry messages every T392 seconds.  Only applies when Annex D is
		bi-directional."
	::= { cdx6500PCTFRDTEPortEntry 10 }

cdx6500frdtepN391 OBJECT-TYPE
	SYNTAX		INTEGER
	ACCESS		read-only
	STATUS		mandatory
	DESCRIPTION
		"Error inactivity threshold.  Number of errors during N393 events
		that cause the station to be declared inactive.  Should be less than
		or equal to N393."
	::= { cdx6500PCTFRDTEPortEntry 12 }

cdx6500frdtepN392 OBJECT-TYPE
	SYNTAX		INTEGER
	ACCESS		read-only
	STATUS		mandatory
	DESCRIPTION
		"Error inactivity threshold.  Number of errors during N393 events
		that cause the station to be declared inactive.  Should be less than
		or equal to N393."
	::= { cdx6500PCTFRDTEPortEntry 13 }

cdx6500frdtepN393 OBJECT-TYPE
	SYNTAX		INTEGER
	ACCESS		read-only
	STATUS		mandatory
	DESCRIPTION
		"Monitored events count for measuring N392.  N392 errors during N393 events
		will cause the station to be declared inactive.  Should be greater than
		N392."
	::= { cdx6500PCTFRDTEPortEntry 14 }

cdx6500frdtepNT1 OBJECT-TYPE
	SYNTAX		INTEGER
	ACCESS		read-only
	STATUS		mandatory
	DESCRIPTION
                "Enquiry Status timer.  FRI port sends status
		enquiry messages to network every nT1 seconds."
	::= { cdx6500PCTFRDTEPortEntry 15 }

cdx6500frdtepNT2 OBJECT-TYPE
	SYNTAX		INTEGER
	ACCESS		read-only
	STATUS		mandatory
	DESCRIPTION
		"Status timer.  FRI port expects the status
		enquiry messages to every nT2 seconds.  Only applies when the
		port is acted as network."
	::= { cdx6500PCTFRDTEPortEntry 16 }

cdx6500frdtepNN1 OBJECT-TYPE
	SYNTAX		INTEGER
	ACCESS		read-only
	STATUS		mandatory
	DESCRIPTION
		"Full Status polling cycle.  FRI port sends Full status
		enquiry messages to network every nN1 polls."
	::= { cdx6500PCTFRDTEPortEntry 17 }

cdx6500frdtepNN2 OBJECT-TYPE
	SYNTAX		INTEGER
	ACCESS		read-only
	STATUS		mandatory
	DESCRIPTION
		"Error inactivity threshold.  Number of errors during NN3 events
		that cause the station to be declared inactive.  Should be less than
		or equal to nN3."
	::= { cdx6500PCTFRDTEPortEntry 18 }

cdx6500frdtepNN3 OBJECT-TYPE
	SYNTAX		INTEGER
	ACCESS		read-only
	STATUS		mandatory
	DESCRIPTION
		"Monitored events count for measuring nN3.  nN2 errors during nN3 events
		will cause the station to be declared inactive.  Should be greater than
		nN3."
	::= { cdx6500PCTFRDTEPortEntry 19 }


-- The Frame Relay DTE Port Statistics Table
-- This table contains Statistics paramaters 
-- for the Frame Relay DTE Port table.

cdx6500PPSTFRDTEPortTable OBJECT-TYPE
	SYNTAX  SEQUENCE OF Cdx6500PPSTFRDTEPortEntry
	ACCESS  not-accessible
	STATUS  mandatory
	DESCRIPTION
		"All of the statistics parameters relevant
		 to the Frame Relay DTE Port table."
	::= { cdx6500PSTPortProtocolGroup 5 }

cdx6500PPSTFRDTEPortEntry OBJECT-TYPE
	SYNTAX  Cdx6500PPSTFRDTEPortEntry
	ACCESS  not-accessible
	STATUS  mandatory
	DESCRIPTION
		"A row of Frame Relay DTE Port statistics parameters."
	INDEX   { cdx6500frdtepStatsPortNum }
	::= { cdx6500PPSTFRDTEPortTable 1 }

Cdx6500PPSTFRDTEPortEntry ::=
	SEQUENCE {
		cdx6500frdtepStatsPortNum
			INTEGER,
		cdx6500frdtepPortStatus
			INTEGER,
		cdx6500frdtepPortSpeed
			INTEGER,
		cdx6500frdtepUtilizationIn
			INTEGER,
		cdx6500frdtepUtilizationOut
			INTEGER,
		cdx6500frdtepCharInTotal
			Counter,
		cdx6500frdtepCharOutTotal
			Counter,
		cdx6500frdtepCharsInPerSec
			INTEGER,
		cdx6500frdtepCharsOutPerSec
			INTEGER,
		cdx6500frdtepFrameInTotal
			Counter,
		cdx6500frdtepFrameOutTotal
			Counter,
		cdx6500frdtepFramesInPerSec
			INTEGER,
		cdx6500frdtepFramesOutPerSec
			INTEGER,
		cdx6500frdtepOverrunErrors
			Counter16,
		cdx6500frdtepUnderrunErrors
			Counter16,
		cdx6500frdtepCRCErrors
			Counter16

		}

cdx6500frdtepStatsPortNum OBJECT-TYPE
	SYNTAX  INTEGER (1..54)
        ACCESS  read-only
	STATUS  mandatory
	DESCRIPTION
		"Specifies a specific port in the network diagram."
	::= { cdx6500PPSTFRDTEPortEntry 1 }

cdx6500frdtepPortStatus OBJECT-TYPE
	SYNTAX		INTEGER {
						disabled(0),
						enabled(1),
						busyOut(2),
						up(3),
						down(4)
						}
	ACCESS		read-only
	STATUS		mandatory
	DESCRIPTION
		"Specifies the current port status.
		Up: Port is operational.
		Disabled: Port has been disabled."
	::= { cdx6500PPSTFRDTEPortEntry 2 }

cdx6500frdtepPortSpeed OBJECT-TYPE
	SYNTAX		INTEGER
	ACCESS		read-only
	STATUS		mandatory
	DESCRIPTION
		"Message transmition speed in bps."
	::= { cdx6500PPSTFRDTEPortEntry 3 }

cdx6500frdtepUtilizationIn OBJECT-TYPE
	SYNTAX		INTEGER (0..100)
	ACCESS		read-only
	STATUS		mandatory
	DESCRIPTION
		"Factor determined by comparison of volume (characters per second) of data
		and clock rate for a specific port."
	::= { cdx6500PPSTFRDTEPortEntry 4 }

cdx6500frdtepUtilizationOut OBJECT-TYPE
	SYNTAX		INTEGER (0..100)
	ACCESS		read-only
	STATUS		mandatory
	DESCRIPTION
		"Factor determined by comparison of volume (characters per second) of data
		and clock rate for a specific port."
	::= { cdx6500PPSTFRDTEPortEntry 5 }

cdx6500frdtepCharInTotal OBJECT-TYPE
	SYNTAX		Counter
	ACCESS		read-only
	STATUS		mandatory
	DESCRIPTION
		"Number of characters received since last boot or statistics reset."
	::= { cdx6500PPSTFRDTEPortEntry 6 }

cdx6500frdtepCharOutTotal OBJECT-TYPE
	SYNTAX		Counter
	ACCESS		read-only
	STATUS		mandatory
	DESCRIPTION
		"Number of characters transmitted since last boot or statistics reset."
	::= { cdx6500PPSTFRDTEPortEntry 7 }

cdx6500frdtepCharsInPerSec OBJECT-TYPE
	SYNTAX		INTEGER
	ACCESS		read-only
	STATUS		mandatory
	DESCRIPTION
		"Average number of characters received per second."
	::= { cdx6500PPSTFRDTEPortEntry 8 }

cdx6500frdtepCharsOutPerSec OBJECT-TYPE
	SYNTAX		INTEGER
	ACCESS		read-only
	STATUS		mandatory
	DESCRIPTION
		"Average number of characters transmitted per second."
	::= { cdx6500PPSTFRDTEPortEntry 9 }

cdx6500frdtepFrameInTotal OBJECT-TYPE
	SYNTAX		Counter
	ACCESS		read-only
	STATUS		mandatory
	DESCRIPTION
		"Number of frames received since last boot or statistics reset."
	::= { cdx6500PPSTFRDTEPortEntry 10 }

cdx6500frdtepFrameOutTotal OBJECT-TYPE
	SYNTAX		Counter
	ACCESS		read-only
	STATUS		mandatory
	DESCRIPTION
		"Number of frames transmitted since last boot or statistics reset."
	::= { cdx6500PPSTFRDTEPortEntry 11 }

cdx6500frdtepFramesInPerSec OBJECT-TYPE
	SYNTAX		INTEGER
	ACCESS		read-only
	STATUS		mandatory
	DESCRIPTION
		"Average number of frames received per second."
	::= { cdx6500PPSTFRDTEPortEntry 12 }

cdx6500frdtepFramesOutPerSec OBJECT-TYPE
	SYNTAX		INTEGER
	ACCESS		read-only
	STATUS		mandatory
	DESCRIPTION
		"Average number of frames transmitted per second."
	::= { cdx6500PPSTFRDTEPortEntry 13 }

cdx6500frdtepOverrunErrors OBJECT-TYPE
	SYNTAX		Counter16
	ACCESS		read-only
	STATUS		mandatory
	DESCRIPTION
		"An input buffer overflowed and characters were discarded."
	::= { cdx6500PPSTFRDTEPortEntry 14 }

cdx6500frdtepUnderrunErrors OBJECT-TYPE
	SYNTAX		Counter16
	ACCESS		read-only
	STATUS		mandatory
	DESCRIPTION
		"Number of errors detected since last node boot or reset of statistics."
	::= { cdx6500PPSTFRDTEPortEntry 15 }

cdx6500frdtepCRCErrors OBJECT-TYPE
	SYNTAX		Counter16
	ACCESS		read-only
	STATUS		mandatory
	DESCRIPTION
		"Number of errors detected by Cyclic Redundancy Check since last node boot
		reset of statistics."
	::= { cdx6500PPSTFRDTEPortEntry 16 }


-- The Frame Relay DTE Station Configuration Table
-- This table contains Configuration paramaters 
-- for the Frame Relay DTE Station table.

cdx6500SPCTFRDTEStationTable OBJECT-TYPE
	SYNTAX  SEQUENCE OF Cdx6500SPCTFRDTEStationEntry
	ACCESS  not-accessible
	STATUS  mandatory
	DESCRIPTION
		"All of the configuration parameters relevant
		 to the Frame Relay DTE Station table."
	::= { cdx6500PCTStationProtocolGroup 2 }

cdx6500SPCTFRDTEStationEntry OBJECT-TYPE
	SYNTAX  Cdx6500SPCTFRDTEStationEntry
	ACCESS  not-accessible
	STATUS  mandatory
	DESCRIPTION
		"A row of Frame Realy DTE station configuration parameters."
	INDEX   { cdx6500frdtesCfgPortNum, cdx6500frdtesCfgDLCI }
	::= { cdx6500SPCTFRDTEStationTable 1 }

Cdx6500SPCTFRDTEStationEntry ::=
	SEQUENCE {
		cdx6500frdtesCfgPortNum
			INTEGER,
		cdx6500frdtesCfgDLCI
			INTEGER,
		cdx6500frdtesStationType
			INTEGER,
		cdx6500frdtesCommInfoRate
			INTEGER,
		cdx6500frdtesCommBurstSize
			INTEGER,
		cdx6500frdtesTransDelay
			INTEGER,
		cdx6500frdtesControlledMode
			INTEGER,
		cdx6500frdtesLinkAddress
			INTEGER,
		cdx6500frdtesPVCChannels
			INTEGER,
		cdx6500frdtesStartingPVC
			INTEGER,
		cdx6500frdtesSVCChannels
			INTEGER,
		cdx6500frdtesStartingSVC
			INTEGER,
		cdx6500frdtesInitialFrame
			INTEGER,
		cdx6500frdtesRetryTimer
			INTEGER,
		cdx6500frdtesPollTimer
			INTEGER,
		cdx6500frdtesTries
			INTEGER,
		cdx6500frdtesFrameWinSize
			INTEGER,
		cdx6500frdtesPacketWinSize
			INTEGER,
                cdx6500frdtesMaxPacketSize
                        INTEGER,
		cdx6500frdtesUpperQueue
			INTEGER,
		cdx6500frdtesLowerQueue
			INTEGER,
		cdx6500frdtesRestartTimer
			INTEGER,
		cdx6500frdtesResetTimer
			INTEGER,
		cdx6500frdtesCallTimer
			INTEGER,
		cdx6500frdtesClearTimer
			INTEGER,
		cdx6500frdtesX25Options
			INTEGER,
		cdx6500frdtesRCDestination
			DisplayString,
		cdx6500frdtesCUG
			DisplayString,
		cdx6500frdtesBillingRecords
			INTEGER,
		cdx6500frdtesStationNum
			INTEGER,
		cdx6500frdtesStnX25Options
			DisplayString
		}

cdx6500frdtesCfgPortNum OBJECT-TYPE
	SYNTAX INTEGER (1..54)
    ACCESS read-only
	STATUS mandatory
	DESCRIPTION
		"FR DTE Port number"
	::= { cdx6500SPCTFRDTEStationEntry 1 }

cdx6500frdtesCfgDLCI OBJECT-TYPE
	SYNTAX INTEGER (16..1007)
    ACCESS read-only
	STATUS mandatory
	DESCRIPTION
		"The Data Link Connection Identifier (dlci) is the unique identifier
		for the station on the FRI Port. Its valid range is 16 - 1007.
		It must match the DLCI configured on the FR Networking Node."
	::= { cdx6500SPCTFRDTEStationEntry 2 }

cdx6500frdtesStationType OBJECT-TYPE
	SYNTAX		INTEGER {
                                annexG(0),
                                bypass(1)
                                }
	ACCESS		read-only
	STATUS		mandatory
	DESCRIPTION
		"Identifies the type of station being configured.

		annexG - This station uses X.25 signaling for layer 3
		bypass  - This station type bypasses layer 3. There is
			  no signaling for SVC's on this station."
	::= { cdx6500SPCTFRDTEStationEntry 3 }

cdx6500frdtesCommInfoRate OBJECT-TYPE
	SYNTAX		INTEGER
	ACCESS		read-only
	STATUS		mandatory
	DESCRIPTION
		"This parameter (CIR) specifies the rate (in bits-per-second) that the  
		Frame Relay network agrees to transfer information under congested 
		conditions for the FRI Station.
		This value is used to throttle data on the FRI station for congestion 
		control purposes.  The CIR cannot be greater than the link speed."
	::= { cdx6500SPCTFRDTEStationEntry 4 }

cdx6500frdtesCommBurstSize OBJECT-TYPE
	SYNTAX		INTEGER
	ACCESS		read-only
	STATUS		mandatory
	DESCRIPTION
		"This parameter (BC) specifies the maximum amount of data (in bits) that 
		the Frame Relay network agrees to transfer over a time interval 
		T = Committed Burst Size / Committed Information Rate.
		Must be > 1/20th of the Committed Information Rate.
		This is used for congestion control purposes."
	::= { cdx6500SPCTFRDTEStationEntry 5 }

cdx6500frdtesTransDelay OBJECT-TYPE
	SYNTAX		INTEGER
	ACCESS		read-only
	STATUS		mandatory
	DESCRIPTION
		"This parameter is the expected one-way delay through the network.
		This is specified in milliseconds."
	::= { cdx6500SPCTFRDTEStationEntry 6 }

cdx6500frdtesControlledMode OBJECT-TYPE
	SYNTAX INTEGER {
                                normal(0),
                                disable(1),
                                congested(2),
                                limit(3)
                                }
	ACCESS		read-only
	STATUS		mandatory
	DESCRIPTION
		"This parameter controls the method of congestion control:

		normal  - congestion control is normal
		disable - never enter Congested State (CTRL)
		congested    - never enter a Non-Congested State (UCTRL)
		limit   - congestion control is normal but limits the
		          data rate to no lower than CIR."
	::= { cdx6500SPCTFRDTEStationEntry 7 }

cdx6500frdtesLinkAddress OBJECT-TYPE
	SYNTAX		INTEGER	{
				dte(0),
                                dce(1)
				}
	ACCESS		read-only
	STATUS		mandatory
	DESCRIPTION
		"The logical link address must be set to complementary values in this FRI 
		station and its corresponding remote FRI station:

		dte - station to have logical DTE address (A)
		dce - station to have logical DCE address (B)"
	::= { cdx6500SPCTFRDTEStationEntry 8 }

cdx6500frdtesPVCChannels OBJECT-TYPE
	SYNTAX		INTEGER
	ACCESS		read-only
	STATUS		mandatory
	DESCRIPTION
		"Number of logical channels used for Permanent Virtual Circuits.
		The total number of PVC and SVC channels on a station (logical link)
		should be kept as small as possible and consistent with needs.
		PVC connections must be configured in the PVC Table."
	::= { cdx6500SPCTFRDTEStationEntry 9 }

cdx6500frdtesStartingPVC OBJECT-TYPE
	SYNTAX		INTEGER
	ACCESS		read-only
	STATUS		mandatory
	DESCRIPTION
		"This is the starting logical channel number for the Permanent Virtual
		Circuits on this FRI station. Not used if the number of PVCs = 0."
	::= { cdx6500SPCTFRDTEStationEntry 10 }

cdx6500frdtesSVCChannels OBJECT-TYPE
	SYNTAX		INTEGER
	ACCESS		read-only
	STATUS		mandatory
	DESCRIPTION
		"Number of logical channels used in Switched Virtual Circuits.
		The total number of PVC and SVC channels on a station (logical link)
		should be kept as small as possible and consistent with needs."
	::= { cdx6500SPCTFRDTEStationEntry 11 }

cdx6500frdtesStartingSVC OBJECT-TYPE
	SYNTAX		INTEGER
	ACCESS		read-only
	STATUS		mandatory
	DESCRIPTION
		"This is the starting logical channel number for the Switched Virtual
		Circuits on this station (logical link). Not used if the number of SVCs = 0."
	::= { cdx6500SPCTFRDTEStationEntry 12 }

cdx6500frdtesInitialFrame OBJECT-TYPE
	SYNTAX		INTEGER {
                                sabm(0),
                                disc(1),
                                none(2)
                                }
	ACCESS		read-only
	STATUS		mandatory
	DESCRIPTION
		"Specify the initial frame required by other end for (logical) link startup:

		none - do nothing (other end initiates link-up)
		sabm - send SABM
		disc - send DISC, then SABM"
	::= { cdx6500SPCTFRDTEStationEntry 13 }

cdx6500frdtesRetryTimer OBJECT-TYPE
	SYNTAX		INTEGER
	ACCESS		read-only
	STATUS		mandatory
	DESCRIPTION
		"T1 link retry timer value in tenths of a second (e.g. 30 = 3.0 seconds)."
	::= { cdx6500SPCTFRDTEStationEntry 14 }

cdx6500frdtesPollTimer OBJECT-TYPE
	SYNTAX		INTEGER
	ACCESS		read-only
	STATUS		mandatory
	DESCRIPTION
		"This sets the time an idle link is probed for assurance of connection
		to the remote FRI station.

		0 - disable the timer
		X - X is in tenths of a second (e.g. 40 = 4.0 seconds) and
		    must be set greater than T1."
	::= { cdx6500SPCTFRDTEStationEntry 15 }

cdx6500frdtesTries OBJECT-TYPE
	SYNTAX		INTEGER
	ACCESS		read-only
	STATUS		mandatory
	DESCRIPTION
		"The maximum number of attempts allowed to complete a transmission."
	::= { cdx6500SPCTFRDTEStationEntry 16 }

cdx6500frdtesFrameWinSize OBJECT-TYPE
	SYNTAX		INTEGER
	ACCESS		read-only
	STATUS		mandatory
	DESCRIPTION
		"Frame level window size must be set to the same value
		at both this FRI station and the remote FRI station."
	::= { cdx6500SPCTFRDTEStationEntry 17 }

cdx6500frdtesPacketWinSize OBJECT-TYPE
	SYNTAX		INTEGER
	ACCESS		read-only
	STATUS		mandatory
	DESCRIPTION
		"Packet level window size must be set to the same value 
		at both this FRI station and the remote FRI station."
	::= { cdx6500SPCTFRDTEStationEntry 18 }

cdx6500frdtesMaxPacketSize OBJECT-TYPE
	SYNTAX		INTEGER {
				psize128(7),
				psize256(8),
				psize512(9),
				psize1024(10)
				}
	ACCESS		read-only
	STATUS		mandatory
	DESCRIPTION
		"This is the maximum X.25 packet size used on the station (logical link).
		For proper operation, this must be set to the same value 
		at both this FRI station and the remote FRI station."
	::= { cdx6500SPCTFRDTEStationEntry 19 }

cdx6500frdtesUpperQueue OBJECT-TYPE
	SYNTAX		INTEGER
	ACCESS		read-only
	STATUS		mandatory
	DESCRIPTION
		"This is the maximum number of data packets a channel on this station
		(logical link) will queue for transmission before invoking flow
		control to the attached channel"
	::= { cdx6500SPCTFRDTEStationEntry 20 }

cdx6500frdtesLowerQueue OBJECT-TYPE
	SYNTAX		INTEGER
	ACCESS		read-only
	STATUS		mandatory
	DESCRIPTION
		"This is the number of data packets a channel on this FRI
		station will have queued for transmission when it releases
		flow control to the attached channel"
	::= { cdx6500SPCTFRDTEStationEntry 21 }

cdx6500frdtesRestartTimer OBJECT-TYPE
	SYNTAX		INTEGER
	ACCESS		read-only
	STATUS		mandatory
	DESCRIPTION
		"Restart-Request timeout timer in seconds. If timer expires on this
		FRI station, the Restart request is sent again."
	::= { cdx6500SPCTFRDTEStationEntry 22 }

cdx6500frdtesResetTimer OBJECT-TYPE
	SYNTAX		INTEGER
	ACCESS		read-only
	STATUS		mandatory
	DESCRIPTION
		"Reset-Request timeout timer in seconds. If timer expires on this
		FRI station, the Reset request is sent again."
	::= { cdx6500SPCTFRDTEStationEntry 23 }

cdx6500frdtesCallTimer OBJECT-TYPE
	SYNTAX		INTEGER
	ACCESS		read-only
	STATUS		mandatory
	DESCRIPTION
		"Call-Request timeout timer in seconds. If timer expires on this
		FRI station, the call is cleared."
	::= { cdx6500SPCTFRDTEStationEntry 24 }

cdx6500frdtesClearTimer OBJECT-TYPE
	SYNTAX		INTEGER
	ACCESS		read-only
	STATUS		mandatory
	DESCRIPTION
		"Clear-Request timeout timer in seconds. If timer expires on this 
		FRI station, the Clear request is sent again."
	::= { cdx6500SPCTFRDTEStationEntry 25 }

cdx6500frdtesX25Options OBJECT-TYPE
	SYNTAX		INTEGER
	ACCESS		read-only
	STATUS		deprecated
	DESCRIPTION
		"Select X.25 options on this station (logical link) as follows:

		NONE  - no option specified
		CUG   - check closed user group; otherwise, CUG passes transparently
		CAUSE - pass cause, diagnostic, code in outbound packets
		HOLD  - hold calls over link restart
		INL   - inter-node link. Link goes to another 6500 device
                DELAY - Enable Delay and Path Trace on this link (link must be
                        connected to Rel. 4.xx node)

		Any combination of above specified by summing (e.g. CUG+CAUSE+. . .).
		NOTE: Please use cdx6500frdtesStnX25Options, which has been added to replace
		this object."
	::= { cdx6500SPCTFRDTEStationEntry 26 }

cdx6500frdtesRCDestination OBJECT-TYPE
	SYNTAX		DisplayString (SIZE(0..255))
	ACCESS		read-only
	STATUS		mandatory
	DESCRIPTION
		"All calls entering this station will be routed to the destination
		specified in this parameter, irrespective of route selection table
		entries. For example, to route all calls to X.25 port 3, use X25-3.
		To route calls to SDLC port 2, station 4, use SDLC-2S4. Blank this
		field to disable this function."
	::= { cdx6500SPCTFRDTEStationEntry 27 }

cdx6500frdtesCUG OBJECT-TYPE
	SYNTAX		DisplayString (SIZE(0..23))
	ACCESS		read-only
	STATUS		mandatory
	DESCRIPTION
		"The station may be a member of up to 8 different Closed User Groups (CUGs).
		Each CUG membership must be a two digit number (except --) and separated
		by a comma. ( e.g. 12,34,56,09,02,03 ).

		--    - No CUG Membership
		00-99 - CUG Membership"
	::= { cdx6500SPCTFRDTEStationEntry 28 }

cdx6500frdtesBillingRecords OBJECT-TYPE
	SYNTAX		INTEGER {
				off(0),
				on(1)
				}
	ACCESS		read-only
	STATUS		mandatory
	DESCRIPTION
		"This controls whether billing (accounting) records will be created for
		calls on this FRI station."
	::= { cdx6500SPCTFRDTEStationEntry 29 }

cdx6500frdtesStationNum OBJECT-TYPE
	SYNTAX		INTEGER
	ACCESS		read-only
	STATUS		mandatory
	DESCRIPTION
		"The number of the logical link on the line.
		This is the value of Sxx for routing purposes."
	::= { cdx6500SPCTFRDTEStationEntry 30 }

cdx6500frdtesStnX25Options OBJECT-TYPE
	SYNTAX		DisplayString (SIZE(0..24))
	ACCESS		read-only
	STATUS		mandatory
	DESCRIPTION
		"Select X.25 options on this station (logical link) as follows:

		NONE  - no option specified
		CUG   - check closed user group; otherwise, CUG passes transparently
		CAUSE - pass cause, diagnostic, code in outbound packets
		HOLD  - hold calls over link restart
		INL   - inter-node link. Link goes to another 6500 device
                DELAY - Enable Delay and Path Trace on this link (link must be
                        connected to Rel. 4.xx node)

		Any combination of above specified by summing (e.g. CUG+CAUSE+. . .).
		NOTE: This object has been added to replace cdx6500frdtesX25Options."
	::= { cdx6500SPCTFRDTEStationEntry 31 }


-- The Frame Relay DTE Station Statistics Table
-- This table contains Statistics paramaters
-- for the Frame Relay DTE Station table.

cdx6500SPSTFRDTEStationTable OBJECT-TYPE
	SYNTAX SEQUENCE OF Cdx6500SPSTFRDTEStationEntry
	ACCESS not-accessible
	STATUS mandatory
	DESCRIPTION
		"All of the statistics parameters relevant
		 to the Frame Relay DTE Station (DLCI) table."
	::= { cdx6500PSTStationProtocolGroup 2 }

cdx6500SPSTFRDTEStationEntry OBJECT-TYPE
	SYNTAX Cdx6500SPSTFRDTEStationEntry
	ACCESS not-accessible
	STATUS mandatory
	DESCRIPTION
		"A row of Frame Relay DTE station (DLCI)
                 Statistics parameters."
	INDEX { cdx6500frdtesStatsPortNum, cdx6500frdtesStatsStationNum }
	::= { cdx6500SPSTFRDTEStationTable 1 }

Cdx6500SPSTFRDTEStationEntry ::=
	SEQUENCE {
		cdx6500frdtesStatsPortNum
			INTEGER,
                cdx6500frdtesStatsDLCI
                        INTEGER,
		cdx6500frdtesUtilizationIn
			INTEGER,
		cdx6500frdtesUtilizationOut
			INTEGER,
                cdx6500frdtesMaxSVCCount
                        INTEGER,
                cdx6500frdtesCurrentSVCCount
                        INTEGER,
		cdx6500frdtesCharInTotal
			Counter,
		cdx6500frdtesCharOutTotal
			Counter,
		cdx6500frdtesCharsInPerSec
			INTEGER,
		cdx6500frdtesCharsOutPerSec
			INTEGER,
		cdx6500frdtesPktInTotal
			Counter,
		cdx6500frdtesPktOutTotal
			Counter,
		cdx6500frdtesPktsInPerSec
			INTEGER,
		cdx6500frdtesPktsOutPerSec
			INTEGER,
		cdx6500frdtesPacketsQueued
			INTEGER,
		cdx6500frdtesFrameInTotal
			Counter,
		cdx6500frdtesFrameOutTotal
			Counter,
		cdx6500frdtesFramesInPerSec
			INTEGER,
		cdx6500frdtesFramesOutPerSec
			INTEGER,
		cdx6500frdtesInfoFramesIn
			Counter,
		cdx6500frdtesInfoFramesOut
			Counter,
		cdx6500frdtesRNRFramesIn
			Counter,
		cdx6500frdtesRNRFramesOut
			Counter,
		cdx6500frdtesRRFramesIn
			Counter,
		cdx6500frdtesRRFramesOut
			Counter,
		cdx6500frdtesREJFramesIn
			Counter,
		cdx6500frdtesREJFramesOut
			Counter,
		cdx6500frdtesDataPktsIn
			Counter,
		cdx6500frdtesDataPktsOut
			Counter,
                cdx6500frdtesResetStats
                        INTEGER,
                cdx6500frdtesBoot
                        INTEGER,
                cdx6500frdtesDisable
                        INTEGER,
                cdx6500frdtesEnable
                        INTEGER
		}

cdx6500frdtesStatsPortNum OBJECT-TYPE
	SYNTAX INTEGER (1..54)
        ACCESS read-only
	STATUS mandatory
	DESCRIPTION
		"Specifies a specific port in the network diagram."
	::= { cdx6500SPSTFRDTEStationEntry 1 }

cdx6500frdtesDLCI OBJECT-TYPE
	SYNTAX		INTEGER (16..1007)
	ACCESS		read-only
	STATUS		mandatory
	DESCRIPTION
		"Data Link Connection Identifier is the unique identifier for the station on
		the FRI port and must match the DLCI configured on the Frame Relay
		networking node."
	::= { cdx6500SPSTFRDTEStationEntry 2 }

cdx6500frdtesUtilizationIn OBJECT-TYPE
	SYNTAX		INTEGER (0..100)
	ACCESS		read-only
	STATUS		mandatory
	DESCRIPTION
		"Indicates the quantity of user bytes sent down the link expressed as a
		percentage of the maximum number of bytes that could have been sent."
	::= { cdx6500SPSTFRDTEStationEntry 3 }

cdx6500frdtesUtilizationOut OBJECT-TYPE
	SYNTAX		INTEGER (0..100)
	ACCESS		read-only
	STATUS		mandatory
	DESCRIPTION
		"Indicates the quantity of user bytes sent down the link expressed as a
		percentage of the maximum number of bytes that could have been sent."
	::= { cdx6500SPSTFRDTEStationEntry 4 }

cdx6500frdtesMaxSVCCount OBJECT-TYPE
	SYNTAX		INTEGER
	ACCESS		read-only
	STATUS		mandatory
	DESCRIPTION
		"Maximum number of SVCs available in the network."
	::= { cdx6500SPSTFRDTEStationEntry 5 }

cdx6500frdtesCurrentSVCCount OBJECT-TYPE
	SYNTAX		INTEGER
	ACCESS		read-only
	STATUS		mandatory
	DESCRIPTION
		"Current number of SVCs currently in use."
	::= { cdx6500SPSTFRDTEStationEntry 6 }

cdx6500frdtesCharInTotal OBJECT-TYPE
	SYNTAX		Counter
	ACCESS		read-only
	STATUS		mandatory
	DESCRIPTION
		"Number of characters received since last node boot or statistics reset."
	::= { cdx6500SPSTFRDTEStationEntry 7 }

cdx6500frdtesCharOutTotal OBJECT-TYPE
	SYNTAX		Counter
	ACCESS		read-only
	STATUS		mandatory
	DESCRIPTION
		"Number of characters transmitted since last node boot or statistics reset."
	::= { cdx6500SPSTFRDTEStationEntry 8 }

cdx6500frdtesCharsInPerSec OBJECT-TYPE
	SYNTAX		INTEGER
	ACCESS		read-only
	STATUS		mandatory
	DESCRIPTION
		"Average number of characters received per second."
	::= { cdx6500SPSTFRDTEStationEntry 9 }

cdx6500frdtesCharsOutPerSec OBJECT-TYPE
	SYNTAX		INTEGER
	ACCESS		read-only
	STATUS		mandatory
	DESCRIPTION
		"Average number of characters transmitted per second."
	::= { cdx6500SPSTFRDTEStationEntry 10 }

cdx6500frdtesPktInTotal OBJECT-TYPE
	SYNTAX		Counter
	ACCESS		read-only
	STATUS		mandatory
	DESCRIPTION
		"Number of packets received since last node boot or statistics reset."
	::= { cdx6500SPSTFRDTEStationEntry 11 }

cdx6500frdtesPktOutTotal OBJECT-TYPE
	SYNTAX		Counter
	ACCESS		read-only
	STATUS		mandatory
	DESCRIPTION
		"Number of packets transmitted since last node boot or statistics reset."
	::= { cdx6500SPSTFRDTEStationEntry 12 }

cdx6500frdtesPktsInPerSec OBJECT-TYPE
	SYNTAX		INTEGER
	ACCESS		read-only
	STATUS		mandatory
	DESCRIPTION
		"Average number of packets received per second."
	::= { cdx6500SPSTFRDTEStationEntry 13 }

cdx6500frdtesPktsOutPerSec OBJECT-TYPE
	SYNTAX		INTEGER
	ACCESS		read-only
	STATUS		mandatory
	DESCRIPTION
		"Average number of packets transmitted per second."
	::= { cdx6500SPSTFRDTEStationEntry 14 }

cdx6500frdtesPacketsQueued OBJECT-TYPE
	SYNTAX		INTEGER
	ACCESS		read-only
	STATUS		mandatory
	DESCRIPTION
		"Current number of packets buffered since last node boot or statistics reset."
	::= { cdx6500SPSTFRDTEStationEntry 15 }

cdx6500frdtesFrameInTotal OBJECT-TYPE
	SYNTAX		Counter
	ACCESS		read-only
	STATUS		mandatory
	DESCRIPTION
		"Number of frames received since last node boot or statistics reset."
	::= { cdx6500SPSTFRDTEStationEntry 16 }

cdx6500frdtesFrameOutTotal OBJECT-TYPE
	SYNTAX		Counter
	ACCESS		read-only
	STATUS		mandatory
	DESCRIPTION
		"Number of frames transmitted since last node boot or statistics reset."
	::= { cdx6500SPSTFRDTEStationEntry 17 }

cdx6500frdtesFramesInPerSec OBJECT-TYPE
	SYNTAX		INTEGER
	ACCESS		read-only
	STATUS		mandatory
	DESCRIPTION
		"Average number of frames received per second."
	::= { cdx6500SPSTFRDTEStationEntry 18 }

cdx6500frdtesFramesOutPerSec OBJECT-TYPE
	SYNTAX		INTEGER
	ACCESS		read-only
	STATUS		mandatory
	DESCRIPTION
		"Average number of frames transmitted per second."
	::= { cdx6500SPSTFRDTEStationEntry 19 }

cdx6500frdtesInfoFramesIn OBJECT-TYPE
	SYNTAX		Counter
	ACCESS		read-only
	STATUS		mandatory
	DESCRIPTION
		"Data received since last node boot or statistics reset."
	::= { cdx6500SPSTFRDTEStationEntry 20 }

cdx6500frdtesInfoFramesOut OBJECT-TYPE
	SYNTAX		Counter
	ACCESS		read-only
	STATUS		mandatory
	DESCRIPTION
		"Data transmitted since last node boot or statistics reset."
	::= { cdx6500SPSTFRDTEStationEntry 21 }

cdx6500frdtesRNRFramesIn OBJECT-TYPE
	SYNTAX		Counter
	ACCESS		read-only
	STATUS		mandatory
	DESCRIPTION
		"Used by the DTE or the network to request that the data flow be stopped on
		a particular virtual circuit."
	::= { cdx6500SPSTFRDTEStationEntry 22 }

cdx6500frdtesRNRFramesOut OBJECT-TYPE
	SYNTAX		Counter
	ACCESS		read-only
	STATUS		mandatory
	DESCRIPTION
		"Used by the DTE or the network to request that the data flow be stopped on
		a particular virtual circuit."
	::= { cdx6500SPSTFRDTEStationEntry 23 }

cdx6500frdtesRRFramesIn OBJECT-TYPE
	SYNTAX		Counter
	ACCESS		read-only
	STATUS		mandatory
	DESCRIPTION
		"Used to clear the RNR request."
	::= { cdx6500SPSTFRDTEStationEntry 24 }

cdx6500frdtesRRFramesOut OBJECT-TYPE
	SYNTAX		Counter
	ACCESS		read-only
	STATUS		mandatory
	DESCRIPTION
		"Used to clear the RNR request."
	::= { cdx6500SPSTFRDTEStationEntry 25 }

cdx6500frdtesREJFramesIn OBJECT-TYPE
	SYNTAX		Counter
	ACCESS		read-only
	STATUS		mandatory
	DESCRIPTION
		"A REJ transmitted by a receiver requests retransmission of a frame, due to
		detection of a transmission or frame sequence error."
	::= { cdx6500SPSTFRDTEStationEntry 26 }

cdx6500frdtesREJFramesOut OBJECT-TYPE
	SYNTAX		Counter
	ACCESS		read-only
	STATUS		mandatory
	DESCRIPTION
		"A REJ transmitted by a receiver requests retransmission of a frame, due to
		detection of a transmission or frame sequence error."
	::= { cdx6500SPSTFRDTEStationEntry 27 }

cdx6500frdtesDataPktsIn OBJECT-TYPE
	SYNTAX		Counter
	ACCESS		read-only
	STATUS		mandatory
	DESCRIPTION
		"A packet containing user information."
	::= { cdx6500SPSTFRDTEStationEntry 28 }

cdx6500frdtesDataPktsOut OBJECT-TYPE
	SYNTAX		Counter
	ACCESS		read-only
	STATUS		mandatory
	DESCRIPTION
		"A packet containing user information."
	::= { cdx6500SPSTFRDTEStationEntry 29 }


-- The Frame Relay DTE Station Control objects
-- These objects provide Control parameters
-- for the Frame Relay DTE Stations.

cdx6500frdtesResetStats OBJECT-TYPE
	SYNTAX		INTEGER {
                                reset(1),
                                noReset(2)
                                }
	ACCESS		write-only
	STATUS		mandatory
	DESCRIPTION
		"Resets the specified Frame Relay station statistics.

		1 - Reset station statistics
		2 - Do not reset station statistics"
	::= { cdx6500SPSTFRDTEStationEntry 30 }

cdx6500frdtesBoot OBJECT-TYPE
	SYNTAX		INTEGER {
                                boot(1),
                                noBoot(2)
                                }
	ACCESS		write-only
	STATUS		mandatory
	DESCRIPTION
		"Boots the specified Frame Relay station.

		1 - Boot station
		2 - Do not boot station"
	::= { cdx6500SPSTFRDTEStationEntry 31 }

cdx6500frdtesDisable OBJECT-TYPE
	SYNTAX		INTEGER {
                                disable(1),
                                noDisable(2)
                                }
	ACCESS		write-only
	STATUS		mandatory
	DESCRIPTION
		"Disables the specified Frame Relay station.

		1 - Disable station
		2 - Do not disable station"
	::= { cdx6500SPSTFRDTEStationEntry 32 }

cdx6500frdtesEnable OBJECT-TYPE
	SYNTAX		INTEGER {
                                enable(1),
                                noEnable(2)
                                }
	ACCESS		write-only
	STATUS		mandatory
	DESCRIPTION
		"Enables the specified Frame Relay station.

		1 - Enable station
		2 - Do not enable station"
	::= { cdx6500SPSTFRDTEStationEntry 33 }

END
