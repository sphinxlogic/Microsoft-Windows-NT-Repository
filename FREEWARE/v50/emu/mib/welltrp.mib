-- Wellfleet Trap MIB

                                -- Sept 9 1993


                              -- StonyBrook Services, Inc.
                              -- Kevin Koenig, Ken Packert
                              -- Bohemia, NY 11767
                              -- (516) 567-6060


WellfleetTRAP-MIB DEFINITIONS ::= BEGIN

     IMPORTS
          commServer, wfMib
               FROM Wellfleet-MIB
          DisplayString
               FROM RFC1155-SMI        
          TRAP-TYPE
               FROM RFC-1215;


     wfTrap OBJECT IDENTIFIER ::= { wfMib 26 }


     wfTrapString OBJECT-TYPE
          SYNTAX        DisplayString
          ACCESS        not-accessible
          STATUS        mandatory
          DESCRIPTION   "Generic Wellfleet TRAP"
          ::= { wfTrap 7 }


      wellfleetInfo TRAP-TYPE
          ENTERPRISE   commServer
          VARIABLES    { wfTrapString }
          DESCRIPTION  "Wellfleet Generic Trap"
          --#TYPE      "Wellfleet trap"
          --#SUMMARY   "%s"
          --#ARGUMENTS { 0 }
          --#SEVERITY  INFORMATION
          --#TIMEINDEX 0
          --#STATE     OPERATIONAL
          ::= 2

END
