PCDOS-MIB DEFINITIONS ::= BEGIN

	  IMPORTS
		  mgmt, NetworkAddress, IpAddress, Counter, Gauge,
			  TimeTicks
		      FROM RFC1155-SMI
		  OBJECT-TYPE
		      FROM RFC-1212;

	  mib-2      OBJECT IDENTIFIER ::= { mgmt 1 }
	  desktop    OBJECT IDENTIFIER ::= { mib-2 12 }


	  -- desktop groups

	  pc         OBJECT IDENTIFIER ::= { desktop 1 }
	  dos        OBJECT IDENTIFIER ::= { desktop 2 }
	  cdev       OBJECT IDENTIFIER ::= { desktop 3 }


	  -- the PC group

	  pcCPUType OBJECT-TYPE
	      SYNTAX  DisplayString (SIZE (0..64))
	      ACCESS  read-only
	      STATUS  mandatory
	      DESCRIPTION
		  "CPU type"
	      ::= { pc 1 }


	  pcCoProcessorPresent OBJECT-TYPE
	      SYNTAX  INTEGER {
			yes(1),
			no(2)
	      }
	      ACCESS  read-only
	      STATUS  mandatory
	      DESCRIPTION
		  "NDP (80x87) present flag"
	      ::= { pc 2 }


	  pcROMBIOSdate OBJECT-TYPE
	      SYNTAX  DisplayString (SIZE (0..255))
	      ACCESS  read-only
	      STATUS  mandatory
	      DESCRIPTION
		  "ROM BIOS revision date"
	      ::= { pc 3 }


	  pcNumFloppyDrives OBJECT-TYPE
	      SYNTAX  INTEGER 
	      ACCESS  read-only
	      STATUS  mandatory
	      DESCRIPTION
		  " "
	      ::= { pc 4 }


	  pcFloppyDrive1Size OBJECT-TYPE
	      SYNTAX  INTEGER {
			none(1),
			fd-360Kb(2),
			fd-720Kb(3),
			fd-1-2Mb(4),
			fd-1-44Mb(5),
			fd-2-88Mb(6)
	      }
	      ACCESS  read-only
	      STATUS  mandatory
	      DESCRIPTION
		  "floppy-drive type A:"
	      ::= { pc 5 }


	  pcFloppyDrive2Size OBJECT-TYPE
	      SYNTAX  INTEGER {
			none(1),
			fd-360Kb(2),
			fd-720Kb(3),
			fd-1-2Mb(4),
			fd-1-44Mb(5),
			fd-2-88Mb(6)
	      }
	      ACCESS  read-only
	      STATUS  mandatory
	      DESCRIPTION
		  "floppy-drive type B:"
	      ::= { pc 6 }


	  pcNumHardDrives OBJECT-TYPE
	      SYNTAX  INTEGER 
	      ACCESS  read-only
	      STATUS  mandatory
	      DESCRIPTION
		  "Number of hard disks"
	      ::= { pc 7 }


	  pcHardDrive1Size OBJECT-TYPE
	      SYNTAX  INTEGER 
	      ACCESS  read-only
	      STATUS  mandatory
	      DESCRIPTION
		  " "
	      ::= { pc 8 }

	  pcHardDrive2Size OBJECT-TYPE
	      SYNTAX  INTEGER 
	      ACCESS  read-only
	      STATUS  mandatory
	      DESCRIPTION
		  " "
	      ::= { pc 9 }

	  pcNumSerialPorts OBJECT-TYPE
	      SYNTAX  INTEGER 
	      ACCESS  read-only
	      STATUS  mandatory
	      DESCRIPTION
		  "Number of COMx ports"
	      ::= { pc 10 }


	  pcNumParallelPorts OBJECT-TYPE
	      SYNTAX  INTEGER 
	      ACCESS  read-only
	      STATUS  mandatory
	      DESCRIPTION
		  "Number of LPTx ports"
	      ::= { pc 11 }


	  pcVideoAdapterType OBJECT-TYPE
	      SYNTAX  INTEGER {
		      other(1),
		      ega(2),
		      vga(3)
	      } 
	      ACCESS  read-only
	      STATUS  mandatory
	      DESCRIPTION
		  "Type of video adapter"
	      ::= { pc 12 }


	  -- the DOS group

	  dosProduct OBJECT-TYPE
	      SYNTAX  DisplayString (SIZE (0..255))
	      ACCESS  read-only
	      STATUS  mandatory
	      DESCRIPTION
		  "DOS product string"
	      ::= { dos 1 }

	  dosMajorVer OBJECT-TYPE
	      SYNTAX  INTEGER
	      ACCESS  read-only
	      STATUS  mandatory
	      DESCRIPTION
		  "DOS version/major version"
	      ::= { dos 2 }


	  dosMinorVer OBJECT-TYPE
	      SYNTAX  INTEGER
	      ACCESS  read-only
	      STATUS  mandatory
	      DESCRIPTION
		  "DOS version/minor version"
	      ::= { dos 3 }

	  dosNumFiles OBJECT-TYPE
	      SYNTAX  INTEGER
	      ACCESS  read-only
	      STATUS  mandatory
	      DESCRIPTION
		  "Number of file handles"
	      ::= { dos 4 }

	  dosNumBuffers OBJECT-TYPE
	      SYNTAX  INTEGER
	      ACCESS  read-only
	      STATUS  mandatory
	      DESCRIPTION
		  "number of disk buffers"
	      ::= { dos 5 }

	  dosLastDrive OBJECT-TYPE
	      SYNTAX  DisplayString
	      ACCESS  read-only
	      STATUS  mandatory
	      DESCRIPTION
		  "Last drive letter"
	      ::= { dos 6 }


	  dosShareFlag OBJECT-TYPE
	      SYNTAX  INTEGER  {
		     loaded(1),
		     not-loaded(2)
	      }
	      ACCESS  read-only
	      STATUS  mandatory
	      DESCRIPTION
		  "Flag if SHARE.EXE is resident."
	      ::= { dos 7 }

	  dosANSIFlag OBJECT-TYPE
	      SYNTAX  INTEGER  {
		     loaded(1),
		     not-loaded(2)
	      }
	      ACCESS  read-only
	      STATUS  mandatory
	      DESCRIPTION
		  "Flag if DEVICE=ANSI.SYS installed."
	      ::= { dos 8 }


	  dosMouseFlag OBJECT-TYPE
	      SYNTAX  INTEGER  {
		     loaded(1),
		     not-loaded(2)
	      }
	      ACCESS  read-only
	      STATUS  mandatory
	      DESCRIPTION
		  "Flag if MOUSE.COM/MOUSE.SYS installed."
	      ::= { dos 9 }


	  dosXMSFlag OBJECT-TYPE
	      SYNTAX  INTEGER  {
		     loaded(1),
		     not-loaded(2)
	      }
	      ACCESS  read-only
	      STATUS  mandatory
	      DESCRIPTION
		  "Flag if XMS-API (HIMEM.SYS) provided."
	      ::= { dos 10 }


	  dosXMSSize OBJECT-TYPE
	      SYNTAX  INTEGER  
	      ACCESS  read-only
	      STATUS  mandatory
	      DESCRIPTION
		  "Extended memory size via XMS."
	      ::= { dos 11 }


	  dosEMSFlag OBJECT-TYPE
	      SYNTAX  INTEGER  {
		     loaded(1),
		     not-loaded(2)
	      }
	      ACCESS  read-only
	      STATUS  mandatory
	      DESCRIPTION
		  "Flag if EMS provided (EMM386.EXE)."
	      ::= { dos 12 }


	  dosEMSSize OBJECT-TYPE
	      SYNTAX  INTEGER  
	      ACCESS  read-only
	      STATUS  mandatory
	      DESCRIPTION
		  "Expanded memory size."
	      ::= { dos 13 }


	  -- the CDEV group

	  cdevTable OBJECT-TYPE
	      SYNTAX  SEQUENCE OF TcdevRecord
	      ACCESS  not-accessible
	      STATUS  mandatory
	      DESCRIPTION
		  " The (conceptual) table of character device drivers."
	      ::= { cdev 1 }

	  cdevEntry OBJECT-TYPE
	      SYNTAX  TcdevRecord
	      ACCESS  not-accessible
	      STATUS  mandatory
	      DESCRIPTION
		  "A (conceptual) entry for one character device driver."
	      INDEX { cdevIndex }
	      ::= { cdevTable 1 }
		  
	  TcdevRecord ::=
	       SEQUENCE {
		  cdevIndex     INTEGER,
		  cdevName      DisplayString,
		  cdevAttrib	INTEGER,
		  cdevFile	DisplayString,
		  cdevSize	INTEGER,
		  cdevAddr	DisplayString,
	       }


	 cdevIndex OBJECT-TYPE
	      SYNTAX  INTEGER
	      ACCESS  read-only
	      STATUS  mandatory
	      DESCRIPTION
		  "A unique value for each character device driver."
	      ::= { cdevEntry 1 }


	 cdevName OBJECT-TYPE
	      SYNTAX  DisplayString
	      ACCESS  read-only
	      STATUS  mandatory
	      DESCRIPTION
		  "Unique character device name."
	      ::= { cdevEntry 2 }


	 cdevAttrib OBJECT-TYPE
	      SYNTAX  DisplayString
	      ACCESS  read-only
	      STATUS  mandatory
	      DESCRIPTION
		  "Device driver attributes to DOS."
	      ::= { cdevEntry 3 }


	 cdevFile OBJECT-TYPE
	      SYNTAX  DisplayString
	      ACCESS  read-only
	      STATUS  mandatory
	      DESCRIPTION
		  "File name from DEVICE=fname.sys in CONFIG.SYS."
	      ::= { cdevEntry 4 }


	 cdevSize OBJECT-TYPE
	      SYNTAX  INTEGER
	      ACCESS  read-only
	      STATUS  mandatory
	      DESCRIPTION
		  "Amount of memory used by driver."
	      ::= { cdevEntry 5 }


	 cdevAddr OBJECT-TYPE
	      SYNTAX  DisplayString
	      ACCESS  read-only
	      STATUS  mandatory
	      DESCRIPTION
		  "Hexadecimal address of device header."
	      ::= { cdevEntry 6 }

	  END
